module openconfig-network-policy-ext {

    yang-version "1";

    // namespace
    namespace "http://openconfig.net/yang/network-policy/extension";

    prefix "oc-network-policy-ext";

    import openconfig-extensions { prefix oc-ext; }

    organization
        "SONiC";

    contact
        "SONiC";

    description
        "This module defines configuration and operational state data
        for Network Policy";

    oc-ext:openconfig-version "0.1.0";

    revision "2021-05-03" {
        description
            "Initial public revision";
        reference "0.1.0";
    }

    // OpenConfig specific extensions for module metadata.
    oc-ext:regexp-posix;
    oc-ext:catalog-organization "openconfig";
    oc-ext:origin "openconfig";

    // typedef statements
    typedef app-type {
        type enumeration {
            enum VOICE {
                description "Voice application type";
            }
            enum VOICE_SIGNALING {
                description "Voice signaling application type";
            }
        }
        description
            "Types of application";
    }

    // grouping statements
    grouping network-policy-config {
        description
            "Groups Network Policy attributes";

        leaf number {
            type uint16;
            description
                "Network policy number";
        }
    }

    grouping application-config {
        description
            "Groups Network Policy attributes";

        leaf type {
            type app-type;

            description
                "The media type that defines the primary function of the 
                 application for the policy advertised by an endpoint";
        }

        leaf vlan-id {
            type uint16 {
                range 0..4094;
            }

            description
                "An extension of the VLAN Identifier for the port, as defined in IEEE 802.1P-1998.
                 A value of 1 through 4094 is used to define a valid PVID.
                 A value of 0 shall be used if the device is using priority tagged frames, 
                 meaning that only the 802.1p priority level is significant and the default VID 
                 of the ingress port is being used instead";
        }

        leaf tagged {
            type boolean;
            description
                "A value of 'true' indicates that the application is using a tagged VLAN.
                 A value of 'false' indicates that for the specific application the device either 
                 is using an untagged VLAN or does not support port based VLAN operation.
                 In this case, both the VLAN ID and the Layer 2 priority fields are ignored and 
                 only the DSCP value has relevance";
        }

        leaf priority {
            type uint8 {
                range 0..7;
            }
            description
                "Layer 2 priority class of service (CoS) for the configured VLAN";
        }

        leaf dscp {
            type uint8 {
                range "0..63";
            }
            description
                "DSCP value for the configured VLAN";
        }
    }

    grouping network-policy-application-top {
        description
            "Top-level grouping for Network Policy Application type";

        container applications {
            description
                "Top-level container for network-policy application type configuration and state data";

            list application {
                key "type";
                description
                    "List of Network Policy Application Types";

                leaf type {
                    type leafref {
                        path "../config/type";
                    }
                    description
                        "Reference to the list key";
                }

                container config {
                    description
                        "Configuration data";

                    uses application-config;
                }

                container state {
                    config false;

                    description
                        "Operational state data";

                    uses application-config;
                }
            }
        }
    }

    grouping network-policy-ext-top {
        description
            "Top-level grouping for Network Policy";

        container network-policies {
            description
                "Top-level container for network-policy configuration and state data";

            list network-policy {
                key "number";
                description
                    "List of Network Policies";

                leaf number {
                    type leafref {
                        path "../config/number";
                    }
                    description
                        "Reference to the list key";
                }

                container config {
                    description
                        "Configuration data";

                    uses network-policy-config;
                }

                container state {
                    config false;

                    description
                        "Operational state data";

                    uses network-policy-config;
                }

                uses network-policy-application-top;
            }
        }
    }

    // data definition statements
    uses network-policy-ext-top;
}
