module openconfig-hostapd {

  yang-version "1";

  // namespace
  namespace "http://openconfig.net/yang/hostapd/extension";

  prefix "oc-hostapd";

  import ietf-yang-types {
        prefix yang;
  }
  import openconfig-extensions { prefix oc-ext; }
  import openconfig-interfaces { prefix oc-if; }

  // meta
  organization "OpenConfig working group";

  contact
    "OpenConfig working group
    www.openconfig.net";

  description
    "This module defines configuration and operational state data
    for authentication manager.";

  oc-ext:openconfig-version "0.1.0";

  revision "2021-07-12" {
    description
      "Initial public revision";
    reference "0.1.0";
  }

  // OpenConfig specific extensions for module metadata.
  oc-ext:regexp-posix;
  oc-ext:catalog-organization "openconfig";
  oc-ext:origin "openconfig";

  // identity statements


  // grouping statements

/*
grouping hostapd-client-oper-info-top {
    description
      "Top-level grouping for port specific hostapd connected clients.";

    list entry {
      key "name mac-addr";
      config false;
      description
        "List of interfaces on which mab is enable";

      leaf name {
        type leafref {
          path "../state/name";
        }
        description
          "Reference to hostapd Ethernet interface";
      }

     leaf mac-addr {
        type leafref {
          path "../state/mac-addr";
        }
        description
          "Reference to connected client MAC addr.";
     }

     container state {
          config false;
        description
          "hostapd/dot1x connected clients data.";

	leaf name {
	     type oc-if:base-interface-ref;
             description
           	"Reference to the Ethernet interface";
	}

	leaf mac-addr {
             type yang:mac-address;
             description
                "MAC address of authenticated client.";
        }

	leaf user-name {
             type string {
                length 1..31;
             }
             description
                "Client user name.";
        }
     }
  }
}

grouping hostapd-protocal-stats-top {
    description
      "Top-level grouping for hostapd protocol stats.";

    list mac-addr {
      key "mac-addr";
      config false;
      description
        "List of interfaces on which mab is enable";

      leaf mac-addr {
        type leafref {
          path "../state/mac-addr";
        }
        description
          "Reference to hostapd authenticated client MAC address.";
      }

      container state {
        config false;
        description
          "State data for PAC on interface";

        uses hostapd-protocal-stats-state;
      }
   }
}

grouping hostapd-protocal-stats-state {
    description
      "Grouping for hostapd protocol stats.";

        	leaf mac-addr {
             	    type yang:mac-address;
                    description
                        "MAC address of authenticated client.";
        	}

		leaf dot1x-auth-eapol-frames-rx {
                    type uint8;
                    description
                        "The number of valid EAPOL frames of any type that have been received by this Authenticator.";
                }

                leaf dot1x-auth-eapol-frames-tx {
                    type uint8;
                    description
                        "The number of EAPOL frames of any type that have been transmitted by this Authenticator.";
                }

                leaf dot1x-auth-eapol-start-frames-rx {
                    type uint8;
                    description
                        "The number of EAPOL Start frames that have been received by this Authenticator.";
                }

                leaf dot1x-auth-eapol-logoff-frames-rx {
                    type uint8;
                    description
                        "The number of EAPOL Logoff frames that have been received by this Authenticator.";
                }

                leaf dot1x-auth-eapol-resp-id-frames-rx {
                    type uint8;
                    description
                        "The number of EAP Resp/Id frames that have been received by this Authenticator.";
                }
		
		leaf dot1x-auth-eapol-resp-frames-rx {
                    type uint8;
                    description
                        "The number of valid EAP Response frames (other than Resp/Id frames) that have been received by this Authenticator.";
                }

                leaf dot1x-auth-eapol-req-frames-tx {
                    type uint8;
                    description
                        "The number of EAP Request frames (other than Rq/Id frames) that have been transmitted by this Authenticator.";
                }

                leaf dot1x-auth-eapol-req-id-frames-tx {
                    type uint8;
                    description
                        "The number of EAP Req/Id frames that have been transmitted by this Authenticator.";
                }

                leaf dot1x-auth-invalid-eapol-frames-rx {
                    type uint8;
                    description
                        "The number of EAPOL frames that have been received by this Authenticator in which the frame type is not recognized.";
                }

                leaf dot1x-auth-eap-length-error-frames-rx {
                    type uint8;
                    description
                        "The number of EAPOL frames that have been received by this Authenticator in which the Packet Body Length field is invalid.";
                }
		
		leaf dot1x-auth-last-eapol-frame-version {
                    type uint8;
                    description
                        "The protocol version number carried in the most recently received EAPOL frame.";
                }
}

grouping hostapd-port-oper-top {
    description
      "Top-level grouping for port specific mab feature config";

    list interface { 
      key "name";
      config false;
      description
        "List of interfaces on which mab is enable";

      leaf name {
	type leafref {
          path "../state/name";
        }
        description
          "Reference to hostapd Ethernet interface";
      }

     container state {
          config false;
	description
          "State data for PAC on interface";

        uses hostapd-port-oper-stats-state;
     }
  }
}

  grouping hostapd-port-oper-stats-state {
    description
      "Grouping for mab port parameters";

     leaf name {
      type oc-if:base-interface-ref;
      description
        "Reference to the MAB Ethernet interface";
     }

     leaf protocol-version {
                    type uint8;
                    description
                        "dot1x protocol version.";
                }

                leaf quiet-period {
                        type uint32 {
                           range 10..65535;
                        }
                        units "seconds";
                        description
                        "The initial value of the timer that defines the period
                                during which the Authenticator will not attempt to authenticate the Supplicant.";
                }

                leaf tx-period {
                    type uint8;
                    description
                        "Time time interval between each EAP Request Ids sent to the supplicant.";
                }

                leaf server-timeout {
                    type uint8;
                    description
                        "RADIUS server timeout.";
                }

		leaf max-reqs {
                    type uint8;
                    description
                        "Maximum number of EAP requests (except Req-Ids) to be sent to the supplicant before timing out.";
                }

                leaf max-req-ids {
                    type uint8;
                    description
                        "Maximum number of EAP Req-Ids to be sent to the supplicant before timing out.";
                }
  }
 */

 grouping hostapd-global-config {
    description
      "Global mab configuration";

    leaf dot1x-system-auth-control {
      type boolean;
              description
                  "dot1x/hostapd status Enabled / Disabled.";
     }
 }

  grouping hostapd-global-config-top {
  description
      "Grouping for HOSTAPD global config";

    container config {
      description
        "Global HOSTAPD configuration";
      uses hostapd-global-config;
    }

    container state {
      config false;

      description
        "Global spanning tree state";
      uses hostapd-global-config;
    }
  }

  grouping hostapd-top {
    description
      "Top-level grouping for pac.";

    container hostapd {
      description
        "Top-level container for dot1x/hostapd configuration and
        state data";

    container hostapd-global-config {
	description 
          "hostapd global configuration data.";

        uses hostapd-global-config-top;
    }
    /*
    container hostapd-port-oper-stats {
        description
          "Enclosing container for the list of interface references";

        uses hostapd-port-oper-top;
    }

    container hostapd-client-oper-info {
        description
          "Enclosing container for connected clients on an interface.";

        uses hostapd-client-oper-info-top;
    
    }

    container hostapd-protocal-stats {
        description
          "Enclosing container for connected clients on an interface.";

    uses hostapd-protocal-stats-top;
    
    }
    */
   }
 }

  // data definition statements

  uses hostapd-top;

}
