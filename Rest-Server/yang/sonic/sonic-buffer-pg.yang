module sonic-buffer-pg {
	namespace "http://github.com/Azure/sonic-buffer-pg";
	prefix bpg;

	import sonic-extension {
		prefix sonic-ext;
	}

	import sonic-common {
		prefix cmn;
	}

	import sonic-port {
		prefix prt;
	}

	import sonic-buffer-profile {
		prefix bpf;
	}

	organization
		"SONiC";

	contact
		"SONiC";

	description
		"SONIC BUFFER PG";

	revision 2019-05-15 {
		description
			"Initial revision.";
	}


	container sonic-buffer-pg {

		container BUFFER_PG {

			list BUFFER_PG_LIST {
				key "ifname pg_num";
				sonic-ext:key-pattern "BUFFER_PG|{ifname}|{pg_num}"; //special pattern used for extracting keys from
				//redis-key and fill populate the yang instance
                                // Total list instance = number(key1) * number(key2) * number(key3)
                                sonic-ext:custom-validation ValidateBufferConfCapability;
                                sonic-ext:custom-validation ValidateBufferConfigsInitilized;
                                sonic-ext:custom-validation ValidateDpbBufferPgDeletion;

				leaf ifname {
					type leafref {
						path "/prt:sonic-port/prt:PORT/prt:PORT_LIST/prt:ifname";
					}
					must "(/cmn:operation/cmn:operation = 'DELETE') or " +
							"not(/prt:sonic-port/prt:PORT/prt:PORT_LIST[prt:ifname=current()]/prt:default_lossless_buffer_profile = 'true')" {
						error-app-tag buffer-pg-not-allow-on-interface;
						error-message "Buffer priority group config is not allowed until default-lossless-buffer-profile is disabled";
					}
				}

				leaf pg_num {
					type string {
						pattern "[0-7]?" {
							error-message "Invalid Buffer PG number";
							error-app-tag pg-num-invalid;
						}
					}
					sonic-ext:custom-validation ValidateRangeIndexOverlap;
				}

				leaf profile { //Hash reference key
					type leafref {
						path "/bpf:sonic-buffer-profile/bpf:BUFFER_PROFILE/bpf:BUFFER_PROFILE_LIST/bpf:name";
					}
					must "(/cmn:operation/cmn:operation = 'DELETE') or " +
                                             "((/bpf:sonic-buffer-profile/bpf:BUFFER_PROFILE/bpf:BUFFER_PROFILE_LIST[bpf:name=current()]/bpf:pool = 'ingress_lossless_pool') and " +
							"not(/bpf:sonic-buffer-profile/bpf:BUFFER_PROFILE/bpf:BUFFER_PROFILE_LIST[bpf:name=current()]/bpf:type = 'egress'))" {
						error-app-tag profile-invalid-for-buffer-pg;
						error-message "Profile config is not valid or Mismatch between PG and Profile types for buffer PG";
					}

					sonic-ext:custom-validation ValidatePoolTypeMatch;
				}
			}
		}
	}
}
