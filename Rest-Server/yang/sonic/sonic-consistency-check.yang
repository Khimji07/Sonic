module sonic-consistency-check {
    namespace "http://github.com/Azure/sonic-consistency-check";
    prefix scc;
    yang-version 1.1;

    organization
        "SONiC";

    contact
        "SONiC";

    description
        "SONiC yang for RPC based Consistency Check.";

    revision 2021-05-18 {
        description
            "Initial revision.";
    }

    typedef access-list-types {
        type enumeration {
            enum MAC;
            enum IPV4;
            enum IPV6;
        }
    }

    rpc start-acl-check {

        description "RPC for triggering Access-list Consistency Checker";

        input {
            leaf acl-name {
                type string;
                description
                    "Configures Consistency Checker for given access-list name";
            }

            leaf acl-type {
                type access-list-types;
                description
                    "Configures Consistency Checker for given access-list type";
            }
        }

        output {
            leaf response {
                type string;
                description
                    "Return message";
            }
        }
    }

    rpc stop-acl-check {

        description "RPC for aborting Access-list Consistency Checker";

        output {
            leaf response {
                type string;
                description
                    "Return status in ascii";
            }
        }
    }

    rpc show-acl-check {

        description "RPC to fetch Access-list Consistency Check status";

        output {
            leaf response {
                type string;
                description
                    "On success, return Access-list Consistency Check in ascii.";
            }
        }
    }

    rpc start-route-check {

        description "RPC for triggering Route Consistency Checker";

        input {
            leaf vrf-name {
                type string;
                default "default";
                description
                    "Configures Consistency Checker for given vrf";
            }

            leaf address-family {
                type enumeration {
                    enum "ipv4";
                    enum "ipv6";
                }
                default "ipv4";
                description
                    "Address family(IPv4/IPv6)";
            }
        }

        output {
            leaf response {
                type string;
                description
                    "Return message";
            }
        }
    }

    rpc stop-route-check {

        description "RPC for aborting Route Consistency Checker";

        output {
            leaf response {
                type string;
                description
                    "Return status in ascii";
            }
        }
    }

    rpc show-route-check {

        description "RPC to fetch Route Consistency Check status";

        output {
            leaf response {
                type string;
                description
                    "On success, return Route Consistency Check in ascii.";
            }
        }
    }

    rpc start-check {

        description "RPC for triggering Consistency Checker";

        output {
            leaf response {
                type string;
                description
                    "Return message";
            }
        }
    }

    rpc stop-check {

        description "RPC for aborting Consistency Checker";

        output {
            leaf response {
                type string;
                description
                    "Return status in ascii";
            }
        }
    }

    rpc show-check {

        description "RPC to fetch Consistency Check status";

        output {
            leaf response {
                type string;
                description
                    "On success, return Consistency Check in ascii.";
            }
        }
    }

}
