module sonic-system-clock {
    namespace "http://github.com/Azure/sonic-system-clock";
    prefix system-clock;
    yang-version 1.1;

    import sonic-extension {
        prefix sonic-ext;
    }

    organization
        "SONiC";

    contact
        "SONiC";

    description
        "SONIC CLOCK";

    revision 2021-09-16 {
        description
            "Initial revision.";
    }

    container sonic-system-clock {

        container CLOCK {

            list CLOCK_LIST {
                
                key "systemclock_key";

                max-elements 1;

                leaf systemclock_key {
                    type enumeration {
                        enum system;
                    }
                    description
                        "system clock timezone key";
                }

                leaf timezone_name {
                    sonic-ext:custom-validation ValidateTimezoneName;
                    type string;
                    description
                        "Standard timezones defined in
                        /usr/share/zoneinfo";
                        reference "IANA Time Zone Database
                                  http://www.iana.org/time-zones";
                }     
            }
        }
    }
}
