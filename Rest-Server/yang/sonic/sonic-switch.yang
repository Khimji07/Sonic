module sonic-switch {
    namespace "http://github.com/Azure/sonic-switch";
    prefix sonic-switch;
    yang-version 1.1;

    import sonic-extension {
        prefix sonic-ext;
    }

    organization
        "SONiC";

    contact
        "SONiC";

    description
        "This module provides rest apis to fetch SWITCH_TABLE db entries.";

    revision 2023-09-14 {
        description
            "Adding support for cut-through switching-mode.";
    }

    revision 2020-09-17 {
        description
            "Adding switch container to config and get MAC aging time.";
    }

    revision 2020-06-26 {
        description
            "Initial revision.";
    }

    typedef switching-mode {
        type enumeration {
            enum CUT_THROUGH {
               description
                  "cut-through switching mode";
            }
            enum STORE_AND_FORWARD {
               description
                  "store-and-forward switching mode";
            }
        }
        description "Enumeration of all possible switching modes";
    }

    typedef hash-algorithm {
        type enumeration {
           enum CRC {
              description "CRC based hash algorithm";
           }
           enum XOR {
              description "XOR-based hash algorithm";
           }
           enum CRC_32LO {
              description "Lower 16-bits of CRC32 based hash algorithm";
           }
           enum CRC_32HI {
              description "Higher 16-bits of CRC32 based hash algorithm";
           }
           enum CRC_CCITT {
              description "CRC using CCITT polynomial based hash algorithm";
           }
           enum CRC_XOR {
              description "Combination of CRC and XOR based hash algorithm";
           }
           enum JENKINS_HASH_LO {
              description "Lower bits of Jenkins hash based hash algorithm";
           }
           enum JENKINS_HASH_HI {
              description "Higher bits of Jenkins hash based hash algorithm";
           }       
        }
        description "Hash algorithm";
    }

    container sonic-switch {

        container SWITCH_TABLE {

             sonic-ext:db-name "APPL_DB";

             config false;
             description
                "Switch_table db entries.";

             list SWITCH_TABLE_LIST {
                key "switch";

                leaf switch {
                      type enumeration {
                           enum switch;
                        }
                      description
                           "switch_table db key.";
                }

                leaf tam_int_ifa_ts_supported {
                    type string {
                        pattern "True|False";
                    }
                        description
                        "Tam int ifa ts feature support status check.";
                }

                leaf drop_monitor_supported {
                    type string {
                        pattern "True|False";
                    }
                        description
                        "Drop monitor feature support status check.";
                }

                leaf snapshot_supported {
                    type string {
                        pattern "True|False";
                    }
                        description
                        "Snapshot feature support status check.";
                }

                leaf threshold_supported {
                    type string {
                        pattern "True|False";
                    }
                        description
                        "Threshold feature support status check.";
                }

                leaf fdb_aging_time {
                    type int32;
                        description
                        "fdb aging time interval.";
                }

                leaf ecmp_hash_seed {
                    type int32;
                        description
                        "ecmp hash seed value.";
                }

                leaf lag_hash_seed {
                    type int32;
                        description
                        "lag hash seed value.";
                }

                leaf rif_cntr_interval {
                    type int32;
                        description
                        "rif counter time interval.";
                }

                leaf vlan_mapping_supported {
                    type string {
                        pattern "True|False";
                    }
                        description
                        "Vlan mapping feature support status check.";
                }

                leaf uat_mode_supported {
                    type string {
                        pattern "True|False";
                    }
                        description
                        "Uat mode feature support status check.";
                }
                leaf switching_mode {
                    sonic-ext:custom-validation ValidateSwitchingModeOpcode;
                    sonic-ext:custom-validation IsSwitchingModeCutThroughConfigurable;
                    type switching-mode;
                    description "Mode for packet switching";
                    default STORE_AND_FORWARD;
                }

                leaf switching_mode_cut_through_supported {
                    type string {
                        pattern "True|False";
                    }
                    description
                        "Cut-through Switching mode feature support status check.";
                }

                leaf versatile_hash_supported {
                    type string {
                        pattern "True|False";
                    }
                    description
                        "Versatile Hash feature support status check.";
                }

                leaf pfc_prio_to_priority_group_mapping_supported {
                    type string {
			            pattern "True|False";
                    }
			        description
			            "PFC priority to PG(priority group) mapping feature support status check.";
                }
                
                leaf ars_supported {
                    type string {
                        pattern "True|False";
                    }
                        description
                        "ARS feature support status check.";
                }
            }
        }

        container SWITCH {
            list SWITCH_LIST {
                key "switch";
                        sonic-ext:custom-validation ValidateSwitchOper;

                leaf switch {
                      type enumeration {
                           enum switch;
                      }
                      description
                           "switch db key.";
                }

                leaf fdb_aging_time {
                    type uint32 {
                      range "0..1000000" {
                         error-message "Invalid FDB aging time interval.";
                      }
                    }
                    default 600;
                        description
                        "FDB aging time interval.";
                }

                leaf rif_cntr_interval {
                      type uint32 {
                         range "1..10000" {
                            error-message "Invalid RIF counter interval.";
                         }
                      }
                      default 5;
                        description
                        "rif counter time interval.";
                }

                leaf buffer_mode_lossless {
                    type boolean;
                        description
                        "Lossless buffer init configuration.";
                }

                leaf roce_enable {
                    type boolean;
                        description
                        "ROCE configuration.";
                }

                leaf switching_mode {
                    sonic-ext:custom-validation ValidateSwitchingModeOpcode;
                    sonic-ext:custom-validation IsSwitchingModeCutThroughConfigurable;
                    type switching-mode;
                    description "Mode for packet switching";
                    default STORE_AND_FORWARD;
                }

                leaf ecmp_hash_algorithm {
                    sonic-ext:custom-validation IsHashSupported;
                    type hash-algorithm;
                        description
                        "ecmp hash algorithm.";
                }
                leaf roce_pfc_priority {
                    type string {
                        pattern "[0-7](,[0-7])?"{
                            error-message "Invalid PFC priority configuration";
                        }
                    }
                }

            }
        }
    }
}
