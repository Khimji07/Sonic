module sonic-system-infra {
    namespace "http://github.com/Azure/sonic-system-infra";
    prefix sonic-sinfra;
    yang-version 1;

    import sonic-common {
        prefix cmn;
    }

    organization
        "SONiC";

    contact
        "SONiC";

    description
        "System Infra rpc commands";

    revision 2020-05-27 {
        description
            "Initial revision.";
    }

    rpc config {
        description
            "Switch config operations:
                - reload: Clear current configuration and import a..."; 
        input {
            leaf param {
                type string {
                    pattern "reload";
                }
                description
                    "String for reload command";
            }
        }
        output {
            leaf result {
                type string;
                description
                    "String showing the result of the last requested command (reload).";
            }
        }
    }

    grouping radv_daemon_config {
        leaf radv_daemon {
            type cmn:mode-enable;
            default disable;
            description "Indicates whether radv daemon is enabled inside radv docker or not, default is not enabled.";
        }
    }

    container sonic-system-infra {
        container RADVDAEMON {
            list RADVDAEMON_LIST {
                key "id"; 
                max-elements 1;
                leaf id {
                    type uint8;
                    description
                        "Key attribute for the table";
                }
                
                uses radv_daemon_config;
            }

        }
    }

}
