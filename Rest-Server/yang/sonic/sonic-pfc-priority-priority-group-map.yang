module sonic-pfc-priority-priority-group-map {
	namespace "http://github.com/Azure/sonic-pfc-priority-priority-group-map";
	prefix pppg;
	import sonic-extension {
        	prefix sonic-ext;
	}

	organization
		"SONiC";

	contact
		"SONiC";

	description
		"SONIC PFC_PRIORITY_TO_PRIORITY_GROUP_MAP";

	revision 2023-12-12 {
		description
			"Initial revision.";
	}

	container sonic-pfc-priority-priority-group-map {	

		container PFC_PRIORITY_TO_PRIORITY_GROUP_MAP {

			list PFC_PRIORITY_TO_PRIORITY_GROUP_MAP_LIST {
				key "name";
				sonic-ext:custom-validation ValidatePfcPriorityToPriorityGroupMapLimits;
				sonic-ext:custom-validation ValidatePfcPriorityToPriorityGroupMapSupport;

				leaf name {
                        		type string {
                        			pattern '[a-zA-Z0-9]{1}([-a-zA-Z0-9_]{0,31})';
                                		length 1..32;
                        		}
				}

				list PFC_PRIORITY_TO_PRIORITY_GROUP_MAP { //this is list inside list for storing mapping between two fields
					key "pfc_priority";

					leaf pfc_priority {
						type string {
							pattern "[0-7]?"{
								error-message "Invalid PFC Priority";
								error-app-tag pfc-priority-invalid;
							}
						}
					}
                                        leaf pg_num {
						type string {
							pattern "[0-7]?"{
								error-message "Invalid Priority Group number";
								error-app-tag pg-num-invalid;
							}
						}
					}
				}

			}
		}
	}
}
