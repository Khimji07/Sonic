module sonic-device-metadata-state {
	yang-version 1.1;
	namespace "http://github.com/Azure/sonic-device-metadata-state";
	prefix sdms;

	import sonic-extension {
		prefix sonic-ext;
	}

	organization
		"SONiC";

	contact
		"SONiC";

	description
		"SONIC DEVICE METADATA";

        revision 2023-06-19 {
            description "Add support for resource_stats_polling_interval.";
        }

	revision 2022-10-12 {
		description
			"Initial revision.";
	}

	container sonic-device-metadata-state {

		container DEVICE_METADATA_STATE {
			config false;
			sonic-ext:db-name "STATE_DB";
			sonic-ext:key-delim "|";

			list DEVICE_METADATA_STATE_LIST {
				key "name";
				max-elements 1;

				leaf name{
					type string;
				}

				leaf intf_naming_mode {
					type enumeration {
						enum standard;
						enum standard-ext;
						enum native;
					}
					default "native";
				}

                                leaf resource_stats_polling_interval {
                                        type uint32 {
                                            range "120..3600";
                                        }
                                        default 120;
                                        units "seconds";
                                        description "Polling interval to retrieve system resource utilization metrics like CPU, Memory etc., valid range is 120 to 3600 seconds.";
                                }

			}
		}
	}

}
