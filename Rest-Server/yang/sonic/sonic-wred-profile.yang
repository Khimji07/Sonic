module sonic-wred-profile {
    namespace "http://github.com/Azure/sonic-wred-profile";
    prefix wrd;
    yang-version 1.1;

	import sonic-common {
		prefix cmn;
	}

    import sonic-extension {
		prefix sonic-ext;
	}

    organization
        "SONiC";

    contact
        "SONiC";

    description
        "SONIC WRED_PROFILE";

    revision 2023-08-25 {
        description
            "Mark unsupported fields.";
    }

    revision 2019-05-15 {
        description
            "Initial revision.";
    }

    container sonic-wred-profile {

        container WRED_PROFILE {

            list WRED_PROFILE_LIST {
                key "name";
                sonic-ext:custom-validation ValidateAtLeastOneColorEnabled;
                sonic-ext:custom-validation ValidateDeleteThresholds;

                leaf name{
                    type string {
                        pattern '[a-zA-Z0-9]{1}([-a-zA-Z0-9_]{0,31})';
                        length 1..32;
                    }
                }

                leaf yellow_min_threshold {
                    sonic-ext:custom-validation UnsupportedWredFields;
                    type uint64 {
                        range "1000..12480000";
                    }
                }

                leaf green_min_threshold {
                    type uint64 {
                        range "1000..12480000";
                    }
                }

                leaf red_min_threshold {
                    sonic-ext:custom-validation UnsupportedWredFields;
                    type uint64 {
                        range "1000..12480000";
                    }
                }
                leaf yellow_max_threshold {
                    sonic-ext:custom-validation UnsupportedWredFields;
                    type uint64 {
                        range "1000..12480000";
                    }

                    must "(/cmn:operation/cmn:operation = 'DELETE') or ((current()/../yellow_min_threshold) and (current()/../yellow_min_threshold > 0))" {
                         error-message "Yellow max threshold can't be configured without min threshold.";
                    }
                    must "(/cmn:operation/cmn:operation = 'DELETE') or (current() >= current()/../yellow_min_threshold)" {
                         error-message "Yellow max threshold must be greater than or equal to min threshold";
                    }
                }

                leaf green_max_threshold {
                    type uint64 {
                        range "1000..12480000";
                    }
                    must "(/cmn:operation/cmn:operation = 'DELETE') or ((current()/../green_min_threshold) and (current()/../green_min_threshold > 0))" {
                       error-message "Green max threshold can't be configured without min threshold.";
                    }
                    must "(/cmn:operation/cmn:operation = 'DELETE') or (current() >= current()/../green_min_threshold)" {
                       error-message "Green max threshold must be greater than or equal to min threshold";
                    }
                }

                leaf red_max_threshold {
                    sonic-ext:custom-validation UnsupportedWredFields;
                    type uint64 {
                        range "1000..12480000";
                    }

                    must "(/cmn:operation/cmn:operation = 'DELETE') or ((current()/../red_min_threshold) and (current()/../red_min_threshold > 0))" {
                        error-message "Red max threshold can't be configured without min threshold.";
                   }
                   must "(/cmn:operation/cmn:operation = 'DELETE') or (current() >= current()/../red_min_threshold)" {
                        error-message "Red max threshold must be greater than or equal to min threshold";
                   }
                }

                leaf ecn {
                    type enumeration {
                        enum ecn_none;
                        enum ecn_green;
                        enum ecn_yellow;
                        enum ecn_red;
                        enum ecn_green_yellow;
                        enum ecn_green_red;
                        enum ecn_yellow_red; 
                        enum ecn_all;
                    }
                }

                leaf wred_green_enable {
                    type boolean;
                    must "(/cmn:operation/cmn:operation = 'DELETE') or (current() = 'false') or ((current()/../green_min_threshold) and (current()/../green_min_threshold > 0))" {
                        error-message "WRED green can't be enabled without green_min_threshold.";
                    }
                    must "(/cmn:operation/cmn:operation = 'DELETE') or (current() = 'false') or ((current()/../green_max_threshold) and (current()/../green_max_threshold > 0))" {
                        error-message "WRED green can't be enabled without green_max_threshold.";
                    }
                }

                leaf wred_yellow_enable {
                    sonic-ext:custom-validation UnsupportedWredFields;
                    type boolean;
                    must "(/cmn:operation/cmn:operation = 'DELETE') or (current() = 'false') or ((current()/../yellow_min_threshold) and (current()/../yellow_min_threshold > 0))" {
                        error-message "WRED yellow can't be enabled without yellow_min_threshold.";
                    }
                    must "(/cmn:operation/cmn:operation = 'DELETE') or (current() = 'false') or ((current()/../yellow_max_threshold) and (current()/../yellow_max_threshold > 0))" {
                        error-message "WRED yellow can't be enabled without yellow_max_threshold.";
                    }
                }

                leaf wred_red_enable {
                    sonic-ext:custom-validation UnsupportedWredFields;
                    type boolean;
                    must "(/cmn:operation/cmn:operation = 'DELETE') or (current() = 'false') or ((current()/../red_min_threshold) and (current()/../red_min_threshold > 0))" {
                        error-message "WRED red can't be enabled without red_min_threshold.";
                    }
                    must "(/cmn:operation/cmn:operation = 'DELETE') or (current() = 'false') or ((current()/../red_max_threshold) and (current()/../red_max_threshold > 0))" {
                        error-message "WRED red can't be enabled without red_max_threshold.";
                    }
                }

                leaf yellow_drop_probability {
                    sonic-ext:custom-validation UnsupportedWredFields;
                    type uint64 {
                        range "0..100";
                    }
                }

                leaf green_drop_probability {
                    type uint64 {
                        range "0..100";
                    }
                }

                leaf red_drop_probability {
                    sonic-ext:custom-validation UnsupportedWredFields;
                    type uint64 {
                        range "0..100";
                    }
                }
            }
        }
    }
}
