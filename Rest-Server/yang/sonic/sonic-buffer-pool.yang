module sonic-buffer-pool {
    namespace "http://github.com/Azure/sonic-buffer-pool";
    prefix bpl;

    import sonic-extension {
        prefix sonic-ext;
    }

    import sonic-common {
        prefix cmn;
    }

    organization
        "SONiC";

    contact
        "SONiC";

    description
        "SONIC BUFFER POOL";

    revision 2019-05-15 {
        description
            "Initial revision.";
    }

    typedef qos_buffer_type {
        type enumeration {
            enum ingress;
            enum egress;
        }
    }

    typedef qos_buffer_mode {
        type enumeration {
            enum static;
            enum dynamic;
        }
    }

    container sonic-buffer-pool {

        container BUFFER_POOL {

            list BUFFER_POOL_LIST {
                key "name";
                sonic-ext:custom-validation ValidateBufferConfCapability;
                sonic-ext:custom-validation ValidateBufferConfigsInitilized;
                leaf name {
                    type string;
                    sonic-ext:custom-validation ValidateSystemBufferPoolName;
                }

                leaf type {
                    type qos_buffer_type;
                    sonic-ext:custom-validation ValidatePoolTypeForBuffTblRef;
                }

                leaf mode {
                    mandatory true;
                    type qos_buffer_mode;
                    sonic-ext:custom-validation ValidateCreateOnlyAttr;
                }

                leaf size {
                    mandatory true;
                    type uint64;

                    must "current() > current()/../xoff" {
                        error-app-tag size-less-than-xoff;
                        error-message "Pool Size must be greater than xoff";
                    }
                    sonic-ext:custom-validation ValidateSystemPoolModification;
                    sonic-ext:custom-validation ValidateCreateOnlyAttr;
                }

                leaf xoff {
                    type uint64;
                    must "(/cmn:operation/cmn:operation = 'DELETE') or " +
                        "not(current()/../type = 'egress')" {
                            error-app-tag buffer-pool-xoff-egress-not-allowed;
                            error-message "Buffer-pool xoff with type egress not allowed";
                        }

                    must "current() < current()/../size" {
                        error-app-tag size-less-than-xoff;
                        error-message "Pool Size must be greater than xoff";
                    }
                    sonic-ext:custom-validation ValidateBufferLimits;
                    sonic-ext:custom-validation ValidateSystemPoolModification;
                }

                leaf mcqe_size {
                    config false;
                    type uint32;
                    description
                        "Multicast queue size cannot be configured by the user as of now. It is assigned as part of pool creation";
                }

            }
        }
    }

    rpc get-buffer-pool-wm-stats {
        input {
            leaf watermark-stats-type {
                type enumeration {
                       enum bytes;
                       enum percentage;
                }
                description
                   "Input parameter request type bytes or percentage";
            }

            leaf watermark-type {
                 type enumeration {
                       enum watermark;
                       enum persistent-watermark;
                 }
                description
                   "Input parameter watermark type - user watermark or persistent-watermark";
            }

            leaf interface {
                type string;
                description
                   "Input parameter for Interface name or 'device'";
            }
        }
        output {
            list Buffer_pool_list {
                key "Poolname StatsValue_1";

                leaf Poolname {
                    type string;
                    description
                        "Buffer pool name";
                }

                leaf StatsValue_1 {
                    type uint64;
                    description
                        "Buffer pool stats value";
                }

                leaf StatsValue_2 {
                    type uint64;
                    description
                       "Buffer pool stats value";
                }
            }
            leaf status {
                type string;
                description
                    "The details status of the operation execution request..";
            }
        }
    }

    rpc clear-buffer-pool-wm-stats {
        input {
            leaf watermark-type {
                type enumeration {
                     enum watermark;
                     enum persistent-watermark;
                }
                description
                   "Watermark clear request input watermark or persistent-watermark";
            }

            leaf interface {
                type string;
                description
                   "Watermark clear request for given Interface or Device";
            }
        }
        output {
            leaf status {
                type string;
                description
                    "Success / failure in clearing buffer pool watermark counters operation execution request.";
            }
        }
    }
}
