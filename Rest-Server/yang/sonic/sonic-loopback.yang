module sonic-loopback {
    namespace "http://github.com/Azure/sonic-loopback";
    prefix sonic-lo;

    import sonic-common {
        prefix scommon;
    }

    organization
        "SONiC";

    contact
        "SONiC";

    description
        "SONIC LOOPBACK";

    revision 2021-11-09 {
        description
            "Add description leaf in loopback table.";
    }

    revision 2021-08-01 {
        description
            "Add admin_status and oper_status attribute.";
    }

    revision 2020-07-26 {
        description
            "Add separate L2 table for Loopback interface";
    }

    container sonic-loopback {

        container LOOPBACK {

            list LOOPBACK_LIST {
                key "name";

                leaf name {
                    type string {
                            pattern "Loopback([0-9]|[1-8][0-9]|9[0-9]|[1-8][0-9]{2}|" +
                                    "9[0-8][0-9]|99[0-9]|[1-8][0-9]{3}|9[0-8][0-9]{2}|" +
                                    "99[0-8][0-9]|999[0-9]|1[0-5][0-9]{3}|16[0-2][0-9]{2}|163[0-7][0-9]|1638[0-3])";
                   }
                }

                leaf description {
                    type string;
                }

                leaf admin_status {
                    type scommon:admin-status;
                    default up;
                }
             }
        }
        container LOOPBACK_TABLE {
            config false;

            list LOOPBACK_TABLE_LIST {
                key "name";

                leaf name {
                    type string {
                            pattern "Loopback([0-9]|[1-8][0-9]|9[0-9]|[1-8][0-9]{2}|" +
                                    "9[0-8][0-9]|99[0-9]|[1-8][0-9]{3}|9[0-8][0-9]{2}|" +
                                    "99[0-8][0-9]|999[0-9]|1[0-5][0-9]{3}|16[0-2][0-9]{2}|163[0-7][0-9]|1638[0-3])";
                   }
                }

                leaf admin_status {
                    type scommon:admin-status;
                }

                leaf oper_status {
                    type scommon:oper-status;
                }

                leaf description {
                    type string;
                }
            }
        }
    }
}
