module sonic-watermark {
    namespace "http://github.com/Azure/sonic-watermark";
    prefix watermark;
    yang-version 1.1;

    organization
        "SONiC";

    contact
        "SONiC";

    description
        "This module allows configuration of watermark snapshot, telemetry intervals.";

    revision 2020-05-29 {
        description
            "Initial revision.";
    }

    container sonic-watermark {

        container WATERMARK_TABLE {
            description
                "Configuration of watermark telemetry intervals.";

            list WATERMARK_TABLE_LIST {
                key "telemetryIntarvalPrefix";

                leaf telemetryIntarvalPrefix {
                    type enumeration {
                        enum TELEMETRY_INTERVAL;
                    }
                }

                leaf interval {
                    type uint16 {
                        range "1..600" {
                            error-message "watermark telemetry interval value must be in range 1-600.";
                        }
                    }
                    description
                        "configure watermark telementry interval.";
                }
            }
        }

        container SNAPSHOT_TABLE {
            description
                "Configuration of watermark snapshot intervals.";

            list SNAPSHOT_TABLE_LIST {
                key "snapshotIntarvalPrefix";

                leaf snapshotIntarvalPrefix {
                    type enumeration {
                        enum SNAPSHOT_INTERVAL;
                    }
                }

                leaf interval {
                    type uint16 {
                        range "1..600" {
                            error-message "watermark snapshot interval value must be in range 1-600.";
                        }
                    }
                    description
                        "configure watermark snapshot interval.";
                }
            }
        }
    }
}
