module sonic-ssh-common {
    namespace "http://github.com/Azure/sonic-ssh-common";
    prefix ssh-com;
    yang-version 1.1;

    import sonic-extension {
        prefix sonic-ext;
    }

    import sonic-port {
        prefix prt;
    }

    organization
        "SONiC";

    contact
        "SONiC";

    description
        "SONiC SSHD global model";

    revision 2023-11-07 {
        description
            "Initial revision.";
    }

  grouping ssh-common-config {
    description
      "Configuration data for a SSHD";

    leaf max_auth_retries {
      type uint8  {
        range "0..10";
      }
      description
        "Specifies the maximum number of authentication attempts permitted per connection";      
    }

    leaf disable_forwarding {
      type boolean;
      description
        "Disables all forwarding features";      
    }

    leaf permit_root_login {
      type boolean;
      description
        "Specifies whether root can log in using ssh";      
    }


    leaf permit_user_environment {
      type boolean;
      description
        "Specifies whether ssh/environment are processed by sshd(8).";      
    }

    leaf permit_user_rc {
      type boolean;
      description
        "Specifies whether any ssh/rc file is executed";      
    }

    leaf ciphers {
      type string;
      sonic-ext:custom-validation ValidateCiphers;
      description
        "Parameters regarding key exchange.";
    }

    leaf macs {
      type string;
      sonic-ext:custom-validation ValidateMacs;
      description
         "Parameters regarding message authentication code (MAC).";
    }

    leaf kexalgorithms {
      type string;
      sonic-ext:custom-validation ValidateKexAlg;
      description
        "Parameters regarding key exchange.";
    }

    leaf x11_forwarding {
      type boolean;
      description
        "Specifies whether X11 forwarding is permitted";      
    }
  }

    container sonic-ssh-common {

        container SSHD_COMMON {
            list SSHD_COMMON_LIST {
                key "id";

                leaf id {
                    type enumeration {
                        enum GLOBAL;
                    }
                    description
                        "It's value is always GLOBAL";
                }

                uses ssh-common-config;

            }
        }
    }
}
