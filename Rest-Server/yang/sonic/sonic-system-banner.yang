module sonic-system-banner {
    namespace "http://github.com/Azure/sonic-system-banner";
    prefix system-banner;
    yang-version 1.1;

    import sonic-extension {
        prefix sonic-ext;
    }

    organization
        "SONiC";

    contact
        "SONiC";

    description
        "SONIC BANNER";

    revision 2022-10-10 {
        description
            "Initial revision.";
    }

    container sonic-system-banner {

        container BANNER_MESSAGE {

            list BANNER_MESSAGE_LIST {

                key "key";

                max-elements 1;

                leaf key {
                    type enumeration {
                        enum MESSAGE;
                    }
                    description
                        "system banner params key";
                }

                leaf login {
                    type string {
                        length 1..4096 {
                           error-message "valid length for banner message is 1-4096.";
                           error-app-tag system-login-banner-invalid;
                        }
                    }
                    description
                        "Text displayed in banner before login";
                }

                leaf motd {
                    type string {
                        length 1..4096 {
                           error-message "valid length for banner message is 1-4096.";
                           error-app-tag system-motd-banner-invalid;
                        }
                    }
                    description
                        "Text displayed in banner after login";
                }

                leaf login_banner_disable {
                    description
                        "Disable displaying the login banner";
                    type boolean;
                    default "false";
                }

                leaf motd_banner_disable {
                    description
                        "Disable displaying the motd banner";
                    type boolean;
                    default "false";
                }

            }
        }
    }
}
