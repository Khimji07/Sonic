module sonic-loopback-annot {

    yang-version "1";

    namespace "http://openconfig.net/yang/annotation/loopback-annot";
    prefix "sonic-lo-annot";

    import sonic-loopback { prefix sonic-lo; }
    import sonic-extensions { prefix sonic-ext; }


    deviation /sonic-lo:sonic-loopback/sonic-lo:LOOPBACK_TABLE/sonic-lo:LOOPBACK_TABLE_LIST {
        deviate add {
            sonic-ext:db-name "APPL_DB";
        }
    }
}
