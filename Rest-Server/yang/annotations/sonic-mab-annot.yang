module sonic-mab-annot {
    namespace "http://github.com/Azure/sonic-mab-annot";
    prefix mab-annot;
    yang-version 1.1;

    import sonic-extensions { prefix sonic-ext; }
    import sonic-mab { prefix smab; }

    deviation /smab:sonic-mab {
        deviate add {
            sonic-ext:user-role-priv "write:secadmin";
        }
    }
}
