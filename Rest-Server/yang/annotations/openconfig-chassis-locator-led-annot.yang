module openconfig-chassis-locator-led-annot {

    yang-version "1";

    namespace "http://openconfig.net/yang/chassis-loc-led-annot";
    prefix "oc-loc-led-annot";

    import sonic-extensions { prefix sonic-ext; }
    import openconfig-chassis-locator-led { prefix oc-loc-led; }

    deviation /oc-loc-led:locator-led-chassis-on{
        deviate add {
            sonic-ext:rpc-callback "rpc_locator_led_chassis_on_cb";
            sonic-ext:user-role-priv "rpc:netadmin";
        }
    }
    deviation /oc-loc-led:locator-led-chassis-off{
        deviate add {
            sonic-ext:rpc-callback "rpc_locator_led_chassis_off_cb";
            sonic-ext:user-role-priv "rpc:netadmin";
        }
    }
    deviation /oc-loc-led:show-locator-led-chassis{
        deviate add {
            sonic-ext:rpc-callback "rpc_show_locator_led_chassis_cb";
            sonic-ext:user-role-priv "rpc:netadmin";
        }
    }
}
