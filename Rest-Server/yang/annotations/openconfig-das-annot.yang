module openconfig-das-annot {

  yang-version "1.1";

  namespace "http://openconfig.net/yang/annotation/openconfig-das-annot";
  prefix "oc-das-annot";

  import sonic-extensions { prefix sonic-ext; }
  import openconfig-das { prefix oc-das; }

  deviation /oc-das:das {
      deviate add {
          sonic-ext:user-role-priv "write:secadmin";
      }
  }

  deviation /oc-das:das/oc-das:das-global-config-table/oc-das:config {
  deviate add {
      sonic-ext:table-name "DAS_GLOBAL_CONFIG_TABLE";
      sonic-ext:key-transformer "das_global_config_tbl_key_xfmr";
    }
  }

  deviation /oc-das:das/oc-das:das-global-config-table/oc-das:config/oc-das:global-server-key {
    deviate add {
        sonic-ext:field-name "global_server_key";
        sonic-ext:field-transformer "das_global_config_tbl_server_key_value_xfmr";
    }
  }

  deviation /oc-das:das/oc-das:das-global-config-table/oc-das:config/oc-das:encrypted {
    deviate add {
        sonic-ext:field-transformer "das_global_config_tbl_server_key_encrypted_value_xfmr";
    }
  }

  deviation /oc-das:das/oc-das:das-global-config-table/oc-das:config/oc-das:das-admin-mode {
    deviate add {
        sonic-ext:field-transformer "das_global_config_tbl_das_admin_mode_value_xfmr";
    }
  }

  deviation /oc-das:das/oc-das:das-global-config-table/oc-das:config/oc-das:das-port {
    deviate add {
        sonic-ext:field-transformer "das_global_config_tbl_das_port_value_xfmr";
    }
  }

  deviation /oc-das:das/oc-das:das-global-config-table/oc-das:config/oc-das:das-auth-type {
    deviate add {
        sonic-ext:field-transformer "das_global_config_tbl_das_auth_type_value_xfmr";
    }
  }

  deviation /oc-das:das/oc-das:das-global-config-table/oc-das:config/oc-das:ignore-bounce-port {
    deviate add {
        sonic-ext:field-transformer "das_global_config_tbl_ignore_bounce_port_value_xfmr";
    }
  }

  deviation /oc-das:das/oc-das:das-global-config-table/oc-das:config/oc-das:ignore-disable-port {
    deviate add {
        sonic-ext:field-transformer "das_global_config_tbl_ignore_disable_port_value_xfmr";
    }
  }

  deviation /oc-das:das/oc-das:das-global-config-table/oc-das:config/oc-das:ignore-session-key {
    deviate add {
        sonic-ext:field-transformer "das_global_config_tbl_ignore_session_key_value_xfmr";
    }
  }

  deviation /oc-das:das/oc-das:das-global-config-table/oc-das:config/oc-das:ignore-server-key {
    deviate add {
        sonic-ext:field-transformer "das_global_config_tbl_ignore_server_key_value_xfmr";
    }
  }

  deviation /oc-das:das/oc-das:das-global-config-table/oc-das:config/oc-das:das-vrf-name {
    deviate add {
        sonic-ext:field-name "das_vrf_name";
    }
  }

  deviation /oc-das:das/oc-das:das-global-config-table/oc-das:config/oc-das:das-request-timeout {
    deviate add {
        sonic-ext:field-name "das_request_timeout";
        sonic-ext:field-transformer "das_global_config_tbl_das_request_timeout_value_xfmr";
    }
  }

  deviation /oc-das:das/oc-das:das-global-config-table/oc-das:state {
  deviate add {
      sonic-ext:table-name "DAS_GLOBAL_CONFIG_TABLE";
      sonic-ext:key-transformer "das_global_config_tbl_key_xfmr";
    }
  }

  deviation /oc-das:das/oc-das:das-global-config-table/oc-das:state/oc-das:global-server-key {
    deviate add {
        sonic-ext:field-name "global_server_key";
        sonic-ext:field-transformer "das_global_config_tbl_server_key_value_xfmr";
    }
  }

  deviation /oc-das:das/oc-das:das-global-config-table/oc-das:state/oc-das:encrypted {
    deviate add {
        sonic-ext:field-transformer "das_global_config_tbl_server_key_encrypted_value_xfmr";
    }
  }

  deviation /oc-das:das/oc-das:das-global-config-table/oc-das:state/oc-das:das-admin-mode {
    deviate add {
        sonic-ext:field-transformer "das_global_config_tbl_das_admin_mode_value_xfmr";
    }
  }

  deviation /oc-das:das/oc-das:das-global-config-table/oc-das:state/oc-das:das-port {
    deviate add {
        sonic-ext:field-transformer "das_global_config_tbl_das_port_value_xfmr";
    }
  }

  deviation /oc-das:das/oc-das:das-global-config-table/oc-das:state/oc-das:das-auth-type {
    deviate add {
        sonic-ext:field-transformer "das_global_config_tbl_das_auth_type_value_xfmr";
    }
  }

  deviation /oc-das:das/oc-das:das-global-config-table/oc-das:state/oc-das:ignore-bounce-port {
    deviate add {
        sonic-ext:field-transformer "das_global_config_tbl_ignore_bounce_port_value_xfmr";
    }
  }

  deviation /oc-das:das/oc-das:das-global-config-table/oc-das:state/oc-das:ignore-disable-port {
    deviate add {
        sonic-ext:field-transformer "das_global_config_tbl_ignore_disable_port_value_xfmr";
    }
  }

  deviation /oc-das:das/oc-das:das-global-config-table/oc-das:state/oc-das:ignore-session-key {
    deviate add {
        sonic-ext:field-transformer "das_global_config_tbl_ignore_session_key_value_xfmr";
    }
  }

  deviation /oc-das:das/oc-das:das-global-config-table/oc-das:state/oc-das:ignore-server-key {
    deviate add {
        sonic-ext:field-transformer "das_global_config_tbl_ignore_server_key_value_xfmr";
    }
  }

  deviation /oc-das:das/oc-das:das-global-config-table/oc-das:state/oc-das:das-vrf-name {
    deviate add {
        sonic-ext:field-name "das_vrf_name";
    }
  }

  deviation /oc-das:das/oc-das:das-global-config-table/oc-das:state/oc-das:das-request-timeout {
    deviate add {
        sonic-ext:field-name "das_request_timeout";
        sonic-ext:field-transformer "das_global_config_tbl_das_request_timeout_value_xfmr";
    }
  }

  deviation /oc-das:das/oc-das:das-client-config-table/oc-das:das-client-config-table-entry {
    deviate add {
       sonic-ext:table-name "DAS_CLIENT_CONFIG_TABLE";
       sonic-ext:key-transformer "das_client_config_tbl_key_xfmr";
    }
  }

  deviation /oc-das:das/oc-das:das-client-config-table/oc-das:das-client-config-table-entry/oc-das:config/oc-das:server-key {
    deviate add {
        sonic-ext:field-name "server_key";
        sonic-ext:field-transformer "das_client_config_tbl_server_key_value_xfmr";
    }
  }

  deviation /oc-das:das/oc-das:das-client-config-table/oc-das:das-client-config-table-entry/oc-das:config/oc-das:encrypted {
    deviate add {
        sonic-ext:field-transformer "das_client_config_tbl_encrypted_value_xfmr";
    }
  }

  deviation /oc-das:das/oc-das:das-client-config-table/oc-das:das-client-config-table-entry/oc-das:state/oc-das:server-key {
    deviate add {
        sonic-ext:field-name "server_key";
        sonic-ext:field-transformer "das_client_config_tbl_server_key_value_xfmr";
    }
  }

  deviation /oc-das:das/oc-das:das-client-config-table/oc-das:das-client-config-table-entry/oc-das:state/oc-das:encrypted {
    deviate add {
        sonic-ext:field-transformer "das_client_config_tbl_encrypted_value_xfmr";
    }
  }
  
  deviation /oc-das:das/oc-das:das-global-counter-stats-table {
         deviate add {
                sonic-ext:db-name "COUNTERS_DB";
                sonic-ext:table-name "DAS_GLOBAL_COUNTER_TABLE";
                sonic-ext:key-transformer "das_global_counter_stats_table_key_xfmr";
         }
  }

  deviation /oc-das:das/oc-das:das-global-counter-stats-table/oc-das:state/oc-das:num-coa-requests-received {
         deviate add {
                sonic-ext:field-transformer "das_gbl_counter_stats_num_coa_reqs_revd_fld_xfmr";
         }
  }

  deviation /oc-das:das/oc-das:das-global-counter-stats-table/oc-das:state/oc-das:num-coa-ack-responses-sent {
         deviate add {
                sonic-ext:field-transformer "das_gbl_counter_stats_num_coa_ack_responses_sent_fld_xfmr";
         }
  }

  deviation /oc-das:das/oc-das:das-global-counter-stats-table/oc-das:state/oc-das:num-coa-nak-responses-sent {
         deviate add {
                sonic-ext:field-transformer "das_gbl_counter_stats_num_coa_nak_responses_sent_fld_xfmr";
         }
  }

  deviation /oc-das:das/oc-das:das-global-counter-stats-table/oc-das:state/oc-das:num-coa-requests-ignored {
         deviate add {
                sonic-ext:field-transformer "das_gbl_counter_stats_num_coa_reqs_ignored_fld_xfmr";
         }
  }

  deviation /oc-das:das/oc-das:das-global-counter-stats-table/oc-das:state/oc-das:num-coa-missing-unsupported-attributes-requests {
         deviate add {
                sonic-ext:field-transformer "das_gbl_counter_stats_num_coa_missing_unsup_attrs_reqs_fld_xfmr";
         }
  }

  deviation /oc-das:das/oc-das:das-global-counter-stats-table/oc-das:state/oc-das:num-coa-session-context-not-found-requests {
         deviate add {
                sonic-ext:field-transformer "das_gbl_counter_stats_num_coa_session_cxt_not_found_reqs_fld_xfmr";
         }
  }

  deviation /oc-das:das/oc-das:das-global-counter-stats-table/oc-das:state/oc-das:num-coa-invalid-attribute-value-requests {
         deviate add {
                sonic-ext:field-transformer "das_gbl_counter_stats_num_coa_invalid_attr_val_reqs_fld_xfmr";
         }
  }

  deviation /oc-das:das/oc-das:das-global-counter-stats-table/oc-das:state/oc-das:num-coa-administratively-prohibited-requests {
         deviate add {
                sonic-ext:field-transformer "das_gbl_counter_stats_num_coa_admin_prohibited_reqs_fld_xfmr";
         }
  }

  deviation /oc-das:das/oc-das:das-client-counter-stats-table {
         deviate add {
                sonic-ext:db-name "COUNTERS_DB";
         }
  }

  deviation /oc-das:das/oc-das:das-client-counter-stats-table/oc-das:das-client-counter-stats-table-entry {
           deviate add {
                  sonic-ext:table-name "DAS_CLIENT_COUNTER_TABLE";
                  sonic-ext:key-transformer "das_client_counter_stats_table_key_xfmr";
           }
  }
  
  deviation /oc-das:das/oc-das:das-client-counter-stats-table/oc-das:das-client-counter-stats-table-entry/oc-das:state/oc-das:num-coa-requests-received {
         deviate add {
                sonic-ext:field-name "num_coa_requests_received";
         }
  }

  deviation /oc-das:das/oc-das:das-client-counter-stats-table/oc-das:das-client-counter-stats-table-entry/oc-das:state/oc-das:num-coa-ack-responses-sent {
         deviate add {
                sonic-ext:field-name "num_coa_ack_responses_sent";
         }
  }

  deviation /oc-das:das/oc-das:das-client-counter-stats-table/oc-das:das-client-counter-stats-table-entry/oc-das:state/oc-das:num-coa-nak-responses-sent {
         deviate add {
                sonic-ext:field-name "num_coa_nak_responses_sent";
         }
  }

  deviation /oc-das:das/oc-das:das-client-counter-stats-table/oc-das:das-client-counter-stats-table-entry/oc-das:state/oc-das:num-coa-requests-ignored {
         deviate add {
                sonic-ext:field-name "num_coa_requests_ignored";
         }
  }

  deviation /oc-das:das/oc-das:das-client-counter-stats-table/oc-das:das-client-counter-stats-table-entry/oc-das:state/oc-das:num-coa-missing-unsupported-attributes-requests {
         deviate add {
                sonic-ext:field-name "num_coa_missing_unsupported_attributes_requests";
         }
  }

  deviation /oc-das:das/oc-das:das-client-counter-stats-table/oc-das:das-client-counter-stats-table-entry/oc-das:state/oc-das:num-coa-session-context-not-found-requests {
         deviate add {
                sonic-ext:field-name "num_coa_session_context_not_found_requests";
         }
  }

  deviation /oc-das:das/oc-das:das-client-counter-stats-table/oc-das:das-client-counter-stats-table-entry/oc-das:state/oc-das:num-coa-invalid-attribute-value-requests {
         deviate add {
                sonic-ext:field-name "num_coa_invalid_attribute_value_requests";
         }
  }

  deviation /oc-das:das/oc-das:das-client-counter-stats-table/oc-das:das-client-counter-stats-table-entry/oc-das:state/oc-das:num-coa-administratively-prohibited-requests {
         deviate add {
                sonic-ext:field-name "num_coa_administratively_prohibited_requests";
         }
  }

}
