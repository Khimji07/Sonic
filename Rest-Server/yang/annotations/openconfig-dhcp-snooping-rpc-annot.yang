module openconfig-dhcp-snooping-rpc-annot {
    yang-version "1";

    namespace "http://openconfig.net/yang/annotation/openconfig-dhcp-snooping-rpc-annot";
    prefix "oc-dhcp-snooping-rpc-annot";

    import sonic-extensions { prefix sonic-ext; }
    import openconfig-dhcp-snooping-rpc { prefix oc-dhcp-snooping-rpc; }

    // meta
    organization
       "SONiC";

    contact
       "SONiC";

    description
       "SONIC dhcp-snooping";

    revision 2021-07-27 {
       description
          "Initial revision";
    }

    deviation /oc-dhcp-snooping-rpc:clear-dhcp-snooping-binding {
        deviate add {
            sonic-ext:rpc-callback "rpc_clear_dhcp_snooping_binding";
        }
    }

    deviation /oc-dhcp-snooping-rpc:clear-dhcpv6-snooping-binding {
        deviate add {
            sonic-ext:rpc-callback "rpc_clear_dhcpv6_snooping_binding";
        }
    }

    deviation /oc-dhcp-snooping-rpc:clear-dhcp-snooping-statistics {
      deviate add {
           sonic-ext:rpc-callback "rpc_clear_dhcp_snooping_stats";
           sonic-ext:user-role-priv "rpc:netadmin";
      }
    }

    deviation /oc-dhcp-snooping-rpc:clear-dhcpv6-snooping-statistics {
      deviate add {
           sonic-ext:rpc-callback "rpc_clear_dhcpv6_snooping_stats";
           sonic-ext:user-role-priv "rpc:netadmin";
      }
    }

    deviation /oc-dhcp-snooping-rpc:clear-dhcp-snooping-statistics-detail {
      deviate add {
           sonic-ext:rpc-callback "rpc_clear_dhcp_snooping_stats_detail";
      }
    }

    deviation /oc-dhcp-snooping-rpc:clear-dhcpv6-snooping-statistics-detail {
      deviate add {
           sonic-ext:rpc-callback "rpc_clear_dhcpv6_snooping_stats_detail";
      }
    }

}
