module sonic-routing-policy-sets-annot {
    namespace "http://github.com/Azure/sonic-routing-policy-sets-annot";
    prefix srpolsets-annot;
    yang-version 1.1;

    import sonic-extensions { prefix sonic-ext; }
    import sonic-routing-policy-sets { prefix sonic-rpolicy-sets; }

    deviation /sonic-rpolicy-sets:sonic-routing-policy-sets {
        deviate add {
            sonic-ext:user-role-priv "write:netadmin";
        }
    }
}
