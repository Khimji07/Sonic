module sonic-counters-annot {

    yang-version "1.1";

    namespace "http://openconfig.net/yang/annotation/scnts-annot";
    prefix "scnts-annot";

    import sonic-extensions { prefix sonic-ext; }
    import sonic-counters { prefix scnts; }

    deviation /scnts:interface_counters {
        deviate add {
	    sonic-ext:rpc-callback "rpc_get_interface_counters";
            sonic-ext:user-role-priv "rpc:operator";
        }
    }

    deviation /scnts:get_ethernet_counters {
        deviate add {
            sonic-ext:rpc-callback "rpc_get_ethernet_counters";
            sonic-ext:user-role-priv "rpc:operator";
        }
    }
    deviation /scnts:get_portchannel_counters {
        deviate add {
            sonic-ext:rpc-callback "rpc_get_portchannel_counters";
            sonic-ext:user-role-priv "rpc:operator";
        }
    }

    deviation /scnts:clear_relay_counters {
        deviate add {
            sonic-ext:rpc-callback "rpc_clear_relay_counters";
            sonic-ext:user-role-priv "rpc:netadmin";
        }
    }
    deviation /scnts:clear_rif_counters {
        deviate add {
            sonic-ext:rpc-callback "rpc_clear_rif_counters";
            sonic-ext:user-role-priv "rpc:netadmin";
        }
    }
    deviation /scnts:rif_counters {
        deviate add {
            sonic-ext:rpc-callback "rpc_get_rif_counters";
            sonic-ext:user-role-priv "rpc:netadmin";
        }
    }
    deviation /scnts:clear_vxlan_tunnel_counters {
        deviate add {
            sonic-ext:rpc-callback "rpc_clear_vxlan_tunnel_counters";
            sonic-ext:user-role-priv "rpc:netadmin";
        }
    }
    deviation /scnts:vxlan_tunnel_counters {
        deviate add {
            sonic-ext:rpc-callback "rpc_get_vxlan_tunnel_counters";
            sonic-ext:user-role-priv "rpc:netadmin";
        }
    }
    deviation /scnts:drop_counters {
        deviate add {
            sonic-ext:rpc-callback "rpc_get_drop_counters";
            sonic-ext:user-role-priv "rpc:netadmin";
        }
    }
}
