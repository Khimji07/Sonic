module openconfig-poe-annot {

  yang-version "1.1";

  namespace "http://openconfig.net/yang/annotation/openconfig-poe-annot";
  prefix "oc-poe-annot";

  import sonic-extensions { prefix sonic-ext; }
  import openconfig-poe { prefix oc-poe; }

  deviation "/oc-poe:poe" {
  deviate add {
      sonic-ext:user-role-priv "write:netadmin";
    }
  }

  // temporary - will be uncommented later.
  deviation "/oc-poe:poe/oc-poe:global/oc-poe:config" {
  deviate add {
      sonic-ext:table-name "POE";
      sonic-ext:key-transformer "poe_global_key_xfmr";
    }
  }

  deviation "/oc-poe:poe/oc-poe:global/oc-poe:config/oc-poe:power-management-model" {
    deviate add {
      sonic-ext:field-transformer "poe_power_mgmt_model_xfmr";
    }
  }

  deviation "/oc-poe:poe/oc-poe:global/oc-poe:config/oc-poe:power-usage-threshold" {
    deviate add {
      sonic-ext:field-name "power_usage_threshold";
    }
  }

  deviation "/oc-poe:poe/oc-poe:global/oc-poe:config/oc-poe:auto-reset-mode" {
    deviate add {
      sonic-ext:field-name "auto_reset_mode";
    }
  }

  deviation "/oc-poe:poe/oc-poe:global/oc-poe:state" {
    deviate add {
      sonic-ext:db-name "STATE_DB";
      sonic-ext:table-name "POE";
      sonic-ext:key-transformer "poe_global_key_xfmr";
    }
  }

  deviation "/oc-poe:poe/oc-poe:global/oc-poe:state/oc-poe:power-management-model" {
    deviate add {
      sonic-ext:field-transformer "poe_power_mgmt_model_xfmr";
    }
  }

  deviation "/oc-poe:poe/oc-poe:global/oc-poe:state/oc-poe:power-usage-threshold" {
    deviate add {
      sonic-ext:field-name "power_usage_threshold";
    }
  }

  deviation "/oc-poe:poe/oc-poe:global/oc-poe:state/oc-poe:auto-reset-mode" {
    deviate add {
      sonic-ext:field-name "auto_reset_mode";
    }
  }

  deviation "/oc-poe:poe/oc-poe:global/oc-poe:state/oc-poe:max-power-budget" {
    deviate add {
      sonic-ext:field-name "max_power_budget";
    }
  }

  deviation "/oc-poe:poe/oc-poe:global/oc-poe:state/oc-poe:firmware-version" {
    deviate add {
      sonic-ext:field-name "fw_version";
    }
  }

  deviation "/oc-poe:poe/oc-poe:global/oc-poe:state/oc-poe:pse-oper-status" {
    deviate add {
      sonic-ext:field-name "pse_oper_status";
    }
  }

  deviation "/oc-poe:poe/oc-poe:global/oc-poe:state/oc-poe:power-threshold" {
    deviate add {
      sonic-ext:field-transformer "power_threshold_xfmr";
    }
  }

  deviation "/oc-poe:poe/oc-poe:global/oc-poe:state/oc-poe:power-consumption" {
    deviate add {
      sonic-ext:field-transformer "power_consumption_xfmr";
    }
  }

  deviation "/oc-poe:poe/oc-poe:cards/oc-poe:card" {
    deviate add {
      sonic-ext:key-transformer "poe_card_key_xfmr";
      sonic-ext:table-name "POE_CARD";
    }
  }

  deviation "/oc-poe:poe/oc-poe:cards/oc-poe:card/oc-poe:config/oc-poe:power-management-model" {
    deviate add {
      sonic-ext:field-name "power_management_model";
    }
  }

  deviation "/oc-poe:poe/oc-poe:cards/oc-poe:card/oc-poe:config/oc-poe:power-usage-threshold" {
    deviate add {
      sonic-ext:field-name "power_usage_threshold";
    }
  }

  deviation "/oc-poe:poe/oc-poe:cards/oc-poe:card/oc-poe:config/oc-poe:auto-reset-mode" {
    deviate add {
      sonic-ext:field-name "auto_reset_mode";
    }
  }

  deviation "/oc-poe:poe/oc-poe:cards/oc-poe:card/oc-poe:state" {
    deviate add {
      sonic-ext:db-name "STATE_DB";
    }
  }

  deviation "/oc-poe:poe/oc-poe:cards/oc-poe:card/oc-poe:state/oc-poe:power-management-model" {
    deviate add {
      sonic-ext:field-name "power_management_model";
    }
  }

  deviation "/oc-poe:poe/oc-poe:cards/oc-poe:card/oc-poe:state/oc-poe:power-usage-threshold" {
    deviate add {
      sonic-ext:field-name "power_usage_threshold";
    }
  }

  deviation "/oc-poe:poe/oc-poe:cards/oc-poe:card/oc-poe:state/oc-poe:auto-reset-mode" {
    deviate add {
      sonic-ext:field-name "auto_reset_mode";
    }
  }

  deviation "/oc-poe:poe/oc-poe:cards/oc-poe:card/oc-poe:state/oc-poe:max-power-budget" {
    deviate add {
      sonic-ext:field-name "max_power_budget";
    }
  }

  deviation "/oc-poe:poe/oc-poe:cards/oc-poe:card/oc-poe:state/oc-poe:power-threshold" {
    deviate add {
      sonic-ext:field-transformer "power_threshold_xfmr";
    }
  }

  deviation "/oc-poe:poe/oc-poe:cards/oc-poe:card/oc-poe:state/oc-poe:power-consumption" {
    deviate add {
      sonic-ext:field-transformer "power_consumption_xfmr";
    }
  }

  deviation "/oc-poe:poe/oc-poe:cards/oc-poe:card/oc-poe:state/oc-poe:firmware-version" {
    deviate add {
      sonic-ext:field-name "fw_version";
    }
  }

  deviation "/oc-poe:reset-poe" {
    deviate add {
      sonic-ext:rpc-callback "rpc_reset_poe";
      sonic-ext:user-role-priv "rpc:netadmin"; 
    }
  }

  deviation "/oc-poe:clear-counters" {
    deviate add {
      sonic-ext:rpc-callback "rpc_clear_poe_counters";
      sonic-ext:user-role-priv "rpc:netadmin"; 
    }
  }
}
