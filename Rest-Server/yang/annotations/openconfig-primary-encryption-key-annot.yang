module openconfig-primary-encryption-key-annot {

    yang-version "1.1";

    namespace "http://openconfig.net/yang/primary-encryption-key-annot";
    prefix "oc-primary-encryption-key-annot";

    import sonic-extensions { prefix sonic-ext; }

    import openconfig-primary-encryption-key {prefix oc-primary-encryption-key; }

    deviation /oc-primary-encryption-key:primary-encryption-key {
      deviate add {
        sonic-ext:user-role-priv "write:secadmin";
      }
    }

    deviation /oc-primary-encryption-key:primary-encryption-key/oc-primary-encryption-key:state {
      deviate add {
        sonic-ext:db-name "STATE_DB";
        sonic-ext:table-name "PRIMARY_ENCRYPTION_KEY";
        sonic-ext:key-transformer "primary_encryption_key_xfmr";
      }
    }
}
