module sonic-auditlog-annot {

    yang-version "1";

    namespace "http://openconfig.net/Azure/sonic-auditlog-annot";
    prefix "auditlog-annot";

    import sonic-extensions { prefix sonic-ext; }
    import sonic-auditlog { prefix sal; }

    deviation /sal:get-auditlog {
        deviate add {
            sonic-ext:rpc-callback "rpc_getauditlog_cb";
            sonic-ext:user-role-priv "rpc:netadmin,operator,secadmin";
        }
    }

    deviation /sal:clear-auditlog {
      deviate add {
        sonic-ext:rpc-callback "rpc_clearauditlog_cb";
        sonic-ext:user-role-priv "rpc:secadmin";
      }
    }

}
