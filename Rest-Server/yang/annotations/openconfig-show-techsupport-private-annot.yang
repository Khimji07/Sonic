module openconfig-show-techsupport-private-annot {

    yang-version "1.1";

    namespace "http://openconfig.net/yang/show-techsupport-private-annot";
    prefix "oc-show-techsupport-private-annot";

    import sonic-extensions { prefix sonic-ext; }

    import openconfig-show-techsupport-private {prefix oc-show-techsupport-private; }

    deviation /oc-show-techsupport-private:show-techsupport-info {
      deviate add {
        sonic-ext:rpc-callback "rpc_oc_showtech_cb";
        sonic-ext:user-role-priv "rpc:secadmin,netadmin,operator";
      }
    }

    deviation /oc-show-techsupport-private:show-techsupport-cancel {
      deviate add {
        sonic-ext:rpc-callback "rpc_oc_showtech_cancel_cb";
        sonic-ext:user-role-priv "rpc:secadmin,netadmin,operator";
      }
    }

}
