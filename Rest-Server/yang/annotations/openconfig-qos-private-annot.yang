module openconfig-qos-private-annot {

    yang-version "1.1";

    namespace "http://openconfig.net/yang/qos-private-annot";
    prefix "oc-qos-private-annot";

    import sonic-extensions { prefix sonic-ext; }

    import openconfig-qos-private {prefix oc-qos-private; }

    deviation /oc-qos-private:clear-watermarks {
      deviate add {
            sonic-ext:rpc-callback "rpc_watermarks_clear_cb";
            sonic-ext:user-role-priv "rpc:netadmin"; 
      }
    }

    deviation /oc-qos-private:clear-threshold-breach {
        deviate add {
            sonic-ext:rpc-callback "rpc_oc_clear_threshold_breach";
            sonic-ext:user-role-priv "rpc:netadmin"; 
        }
    }

    deviation /oc-qos-private:qos-buffer-config {
        deviate add {
            sonic-ext:rpc-callback "rpc_qos_buffer_config";
            sonic-ext:user-role-priv "rpc:netadmin"; 
        }
    }

    deviation /oc-qos-private:qos-roce-config {
        deviate add {
            sonic-ext:rpc-callback "rpc_qos_roce_config";
        }
    }

}
