module sonic-threshold-annot {

    yang-version "1.1";

    namespace "http://openconfig.net/yang/annotation/sonic-threshold-annot";
    prefix "sthclear-annot";

    import sonic-threshold { prefix threshold; }
    import sonic-extensions { prefix sonic-ext; }

    deviation /threshold:clear-threshold-breach {
        deviate add {
            sonic-ext:rpc-callback "rpc_clear_threshold_breach";
        }
    }
}
