module openconfig-das-rpc-annot {

  yang-version "1.1";

  namespace "http://openconfig.net/yang/annotation/openconfig-das-rpc-annot";
  prefix "oc-das-rpc-annot";

  import sonic-extensions { prefix sonic-ext; }
  import openconfig-das-rpc { prefix oc-das-rpc; }

  deviation /oc-das-rpc:clear-radius-dynamic-author-statistics {
         deviate add {
                sonic-ext:rpc-callback "rpc_clear_radius_dynamic_author_statistics";
                sonic-ext:user-role-priv "rpc:secadmin";
         }
  }
}
