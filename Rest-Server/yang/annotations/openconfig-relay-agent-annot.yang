module openconfig-relay-agent-annot {

    yang-version "1";

    namespace "http://openconfig.net/yang/annotation/oc-relay-annot";
    prefix "oc-relay-annot";

    import openconfig-relay-agent { prefix oc-relay; }
    import sonic-extensions { prefix sonic-ext; }
    import openconfig-relay-agent-ext { prefix oc-relay-ext; }

    revision "2020-04-01" {
    description
      "Moved to subtree-transformers";
    }

    revision "2020-03-11" {
    description
      "Initial release";
    }
   
    deviation /oc-relay:relay-agent {
      deviate add {
         sonic-ext:user-role-priv "write:netadmin";
      }
    }

    deviation /oc-relay:relay-agent/oc-relay:dhcp/oc-relay:interfaces/oc-relay:interface {
      deviate add {
         sonic-ext:table-transformer "relay_agent_table_xfmr";
         sonic-ext:key-transformer "relay_agent_intf_tbl_key_xfmr";
      }
    }

    deviation /oc-relay:relay-agent/oc-relay:dhcp/oc-relay:interfaces/oc-relay:interface/oc-relay:config {
      deviate add {
          sonic-ext:subtree-transformer "relay_agent_config_xfmr";
      }
    }

    deviation /oc-relay:relay-agent/oc-relay:dhcp/oc-relay:interfaces/oc-relay:interface/oc-relay:state {
      deviate add {
          sonic-ext:subtree-transformer "relay_agent_state_xfmr";
      }
    }
     
    deviation /oc-relay:relay-agent/oc-relay:dhcp/oc-relay:interfaces/oc-relay:interface/oc-relay:agent-information-option/oc-relay:config {
      deviate add {
          sonic-ext:subtree-transformer "relay_agent_config_xfmr";
      }
    }

    deviation /oc-relay:relay-agent/oc-relay:dhcp/oc-relay:interfaces/oc-relay:interface/oc-relay:agent-information-option/oc-relay:state {
      deviate add {
          sonic-ext:subtree-transformer "relay_agent_state_xfmr";
      }
    }

   deviation /oc-relay:relay-agent/oc-relay:dhcp/oc-relay:interfaces/oc-relay:interface/oc-relay:state/oc-relay:helper-address {
      deviate add {
         sonic-ext:field-name "dhcp_servers";
      }
    }

    deviation /oc-relay:relay-agent/oc-relay:dhcp/oc-relay:interfaces/oc-relay:interface/oc-relay:state/oc-relay:id {
      deviate add {
         sonic-ext:field-transformer "relay_agent_id_field_xfmr";
      }
    }

    deviation /oc-relay:relay-agent/oc-relay:dhcp/oc-relay:interfaces/oc-relay:interface/oc-relay:state/oc-relay:counters {
      deviate add {
         sonic-ext:subtree-transformer "relay_agent_counters_xfmr";
      }
    }

    deviation /oc-relay:relay-agent/oc-relay:dhcpv6/oc-relay:interfaces/oc-relay:interface {
      deviate add {
         sonic-ext:table-transformer "relay_agent_table_xfmr";
         sonic-ext:key-transformer "relay_agent_intf_tbl_key_xfmr";
      }
    }

    deviation /oc-relay:relay-agent/oc-relay:dhcpv6/oc-relay:interfaces/oc-relay:interface/oc-relay:config {
      deviate add {
         sonic-ext:subtree-transformer "relay_agent_config_xfmr";
      }
    }

    deviation /oc-relay:relay-agent/oc-relay:dhcpv6/oc-relay:interfaces/oc-relay:interface/oc-relay:state {
      deviate add {
         sonic-ext:subtree-transformer "relay_agent_state_xfmr";
      }
    }

     deviation /oc-relay:relay-agent/oc-relay:dhcpv6/oc-relay:interfaces/oc-relay:interface/oc-relay:options/oc-relay:config {
      deviate add {
         sonic-ext:subtree-transformer "relay_agent_config_xfmr";
      }
    }

     deviation /oc-relay:relay-agent/oc-relay:dhcpv6/oc-relay:interfaces/oc-relay:interface/oc-relay:options/oc-relay:state {
      deviate add {
         sonic-ext:subtree-transformer "relay_agent_state_xfmr";
      }
    }

    deviation /oc-relay:relay-agent/oc-relay:dhcpv6/oc-relay:interfaces/oc-relay:interface/oc-relay:state/oc-relay:helper-address {
      deviate add {
         sonic-ext:field-name "dhcpv6_servers";
      }
    }

    deviation /oc-relay:relay-agent/oc-relay:dhcpv6/oc-relay:interfaces/oc-relay:interface/oc-relay:state/oc-relay:id {
      deviate add {
         sonic-ext:field-transformer "relay_agent_id_field_xfmr";
      }
    }

    deviation /oc-relay:relay-agent/oc-relay:dhcpv6/oc-relay:interfaces/oc-relay:interface/oc-relay:state/oc-relay:counters {
      deviate add {
         sonic-ext:subtree-transformer "relay_agent_v6_counters_xfmr";
      }
    }


}
