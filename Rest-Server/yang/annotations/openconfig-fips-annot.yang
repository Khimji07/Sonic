module openconfig-fips-annot {

    yang-version "1.1";

    namespace "http://openconfig.net/yang/annotation/oc-fips-annot";
    prefix "oc-fips-annot";

    import sonic-extensions { prefix sonic-ext; }
    import openconfig-fips { prefix oc-fips; }

    deviation /oc-fips:fips {
      deviate add {
        sonic-ext:table-name "FIPS";
        sonic-ext:key-transformer "fips_key_xfmr";
        sonic-ext:user-role-priv "write:secadmin";
      }
    }

    deviation /oc-fips:fips/oc-fips:config/oc-fips:fips-mode {
      deviate add {
        sonic-ext:field-name "fips_mode";
        sonic-ext:field-transformer "fips_mode_field_xfmr";
      }
    }

    deviation /oc-fips:fips/oc-fips:state/oc-fips:fips-mode {
      deviate add {
        sonic-ext:field-name "fips_mode";
        sonic-ext:field-transformer "fips_mode_field_xfmr";
      }
    }
}
