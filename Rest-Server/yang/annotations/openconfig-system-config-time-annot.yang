module openconfig-system-config-time-annot {

    yang-version "1";

    namespace "http://openconfig.net/yang/openconfig-system-config-time-annot";
    prefix "oc-sys-ct-annot";

    import openconfig-system { prefix oc-sys; }
    import sonic-extensions { prefix sonic-ext; }

    deviation /oc-sys:system/oc-sys:state/oc-sys:config-time {
        deviate add {
            sonic-ext:subscribe-on-change "disable";
        }
    }
}
