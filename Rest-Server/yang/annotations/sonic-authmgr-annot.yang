module sonic-authmgr-annot {
    namespace "http://github.com/Azure/sonic-authmgr-annot";
    prefix authmgr-annot;
    yang-version 1.1;

    import sonic-extensions { prefix sonic-ext; }
    import sonic-authmgr { prefix sauthmgr; }

    deviation /sauthmgr:sonic-authmgr {
	deviate add {
            sonic-ext:user-role-priv "write:secadmin";
        }
    }
}
