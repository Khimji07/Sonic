module openconfig-ip-helper-annot {
    yang-version "1";

    namespace "http://openconfig.net/yang/annotation/openconfig-ip-helper-annot";
    prefix "oc-ip-helper-annot";

    import sonic-extensions { prefix sonic-ext; }
    import openconfig-ip-helper { prefix oc-ip-helper; }

    // meta
    organization
       "SONiC";

    contact
       "SONiC";

    description
       "SONIC ip-helper";

    revision 2020-06-04 {
       description
          "Initial revision";
    }

  deviation /oc-ip-helper:ip-helper {
    deviate add {
      sonic-ext:user-role-priv "write:netadmin";
    }
  }
  
  deviation /oc-ip-helper:ip-helper/oc-ip-helper:config {
    deviate add {
      sonic-ext:table-name "UDP_BROADCAST_FORWARDING";
      sonic-ext:key-transformer "ip_helper_global_key_xfmr";
    }
  }
  
  deviation /oc-ip-helper:ip-helper/oc-ip-helper:config/oc-ip-helper:enable {
    deviate add {
      sonic-ext:field-transformer "ip_helper_enable_xfmr";
    }
  }

  deviation /oc-ip-helper:ip-helper/oc-ip-helper:config/oc-ip-helper:incoming-rate-limit {
    deviate add {
      sonic-ext:field-name "rate_limit_pps";
    }
  }

  deviation /oc-ip-helper:ip-helper/oc-ip-helper:config/oc-ip-helper:ports {
    deviate add {
      sonic-ext:field-name "include_ports";
    }
  }

  deviation /oc-ip-helper:ip-helper/oc-ip-helper:state {
    deviate add {
      sonic-ext:table-name "UDP_BROADCAST_FORWARDING";
      sonic-ext:key-transformer "ip_helper_global_key_xfmr";
    }
  }
  
  deviation /oc-ip-helper:ip-helper/oc-ip-helper:state/oc-ip-helper:enable {
    deviate add {
      sonic-ext:field-transformer "ip_helper_enable_xfmr";
    }
  }

  deviation /oc-ip-helper:ip-helper/oc-ip-helper:state/oc-ip-helper:incoming-rate-limit {
    deviate add {
      sonic-ext:field-name "rate_limit_pps";
    }
  }

  deviation /oc-ip-helper:ip-helper/oc-ip-helper:config/oc-ip-helper:ports {
    deviate add {
      sonic-ext:field-transformer "ip_helper_ports_xfmr";
    }
  }

  deviation /oc-ip-helper:ip-helper/oc-ip-helper:state/oc-ip-helper:ports {
    deviate add {
      sonic-ext:field-name "include_ports";
    }
  }

  deviation /oc-ip-helper:ip-helper/oc-ip-helper:state/oc-ip-helper:exclude-default-ports {
    deviate add {
      sonic-ext:field-transformer "ip_helper_exclude_ports_xfmr";
    }
  }

  deviation /oc-ip-helper:ip-helper {
    deviate add {
      sonic-ext:post-transformer "ip_helper_post_xfmr";
    }
  }

  deviation /oc-ip-helper:ip-helper/oc-ip-helper:interfaces/oc-ip-helper:interface {
    deviate add {
       sonic-ext:table-transformer "ip_helper_table_xfmr";
       sonic-ext:key-transformer "ip_helper_intf_tbl_key_xfmr";
    }
  }

  deviation /oc-ip-helper:ip-helper/oc-ip-helper:interfaces/oc-ip-helper:interface/oc-ip-helper:servers {
    deviate add {
      sonic-ext:subtree-transformer "ip_helper_intf_xfmr";
    }
  }

  deviation /oc-ip-helper:ip-helper/oc-ip-helper:interfaces/oc-ip-helper:interface/oc-ip-helper:state/oc-ip-helper:counters {
    deviate add {
      sonic-ext:db-name "COUNTERS_DB";
      sonic-ext:table-name "COUNTERS_IP_HELPER";
      sonic-ext:key-transformer "ip_helper_interface_counter_key_xfmr";
    }
  }

  deviation /oc-ip-helper:ip-helper/oc-ip-helper:interfaces/oc-ip-helper:interface/oc-ip-helper:state/oc-ip-helper:counters/oc-ip-helper:received-packets {
    deviate add {
      sonic-ext:field-name "PKTS_RECEIVED";
    }
  }

  deviation /oc-ip-helper:ip-helper/oc-ip-helper:interfaces/oc-ip-helper:interface/oc-ip-helper:state/oc-ip-helper:counters/oc-ip-helper:relayed-packets {
    deviate add {
      sonic-ext:field-name "PKTS_RELAYED";
    }
  }

  deviation /oc-ip-helper:ip-helper/oc-ip-helper:interfaces/oc-ip-helper:interface/oc-ip-helper:state/oc-ip-helper:counters/oc-ip-helper:dropped-packets {
    deviate add {
      sonic-ext:field-name "PKTS_DROPPED";
    }
  }

  deviation /oc-ip-helper:ip-helper/oc-ip-helper:interfaces/oc-ip-helper:interface/oc-ip-helper:state/oc-ip-helper:counters/oc-ip-helper:packets-with-invalid-ttl {
    deviate add {
      sonic-ext:field-name "PKTS_INVALID_TTL";
    }
  }

  deviation /oc-ip-helper:ip-helper/oc-ip-helper:interfaces/oc-ip-helper:interface/oc-ip-helper:state/oc-ip-helper:counters/oc-ip-helper:broadcast-packets {
    deviate add {
      sonic-ext:field-name "PKTS_BROADCAST";
    }
  }

  deviation /oc-ip-helper:ip-helper/oc-ip-helper:interfaces/oc-ip-helper:interface/oc-ip-helper:state/oc-ip-helper:counters/oc-ip-helper:net-broadcast-packets {
    deviate add {
      sonic-ext:field-name "PKTS_NET_BROADCAST";
    }
  }

}
