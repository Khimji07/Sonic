module openconfig-vlan-ext {

  yang-version "1";

  namespace "http://openconfig.net/yang/vlan/extension";

  prefix "oc-vlan-ext";

  import openconfig-extensions { prefix oc-ext; }

  // OpenConfig specific extensions for module metadata.
  oc-ext:regexp-posix;

  // meta
  organization
    "OCP SONiC Subproject";

  contact
    "OCP SONiC Subproject Working Group
     https://github.com/Azure/SONiC";

  description
    "This module defines configuration and operational state
    data for vlans.";

  oc-ext:openconfig-version "0.1.0";

  revision "2021-10-21" {
    description
      "Initial revision";
    reference "0.1.0";
  }

   grouping reserve-vlan-config {
    description
      "Grouping for reserved Vlans";
    leaf vlan-name {
      type string;
      description
        "Vlan name";
    }
  }

  grouping reserve-vlan-top {
    description
      "This group contains information about all the reserved vlans";

    container reserve-vlans {
      description
        "Encloseure for list of Vlans";

    list reserve-vlan {
        key "vlan-name";
        max-elements 128;
        description
          "List of reserved Vlans";

        
        leaf vlan-name {
          type leafref {
            path "../config/vlan-name";
          }
          description
            "";
        }

        container config {
          description
            "Reserve Vlan Config data";

          uses reserve-vlan-config;
        }

        container state {
          config false;
          description
            "Vlan state";
          uses reserve-vlan-config;
        }
      }
    }
  }
  
  uses reserve-vlan-top;

}
