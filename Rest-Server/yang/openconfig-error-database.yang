module openconfig-error-database {

  yang-version "1.1";

  //namespace
  namespace "http://openconfig.net/yang/error-database/extension";
  prefix "oc-error-database";

  import openconfig-inet-types { prefix oc-inet; }
  import openconfig-extensions { prefix oc-ext; }
  import openconfig-yang-types { prefix oc-yang; }
  import openconfig-interfaces { prefix oc-if; }

  //meta
  organization
    "SONiC";

  contact
    "SONiC";

  description
    "This module defines configuration and operational state data for Error Database";

  revision "2021-11-07" {
    description
      "Initial draft.";
    reference "1.0.2";
  }

  oc-ext:openconfig-version "1.0.2";

  grouping error-rc-opearation-codes {
    description
      "Grouping for all return codes and operations";

    leaf rc {
      type enumeration {
        enum SWSS_RC_SUCCESS;
        enum SWSS_RC_INVALID_PARAM;
        enum SWSS_RC_UNAVAIL;
        enum SWSS_RC_NOT_FOUND;
        enum SWSS_RC_NO_MEMORY;
        enum SWSS_RC_EXISTS;
        enum SWSS_RC_TABLE_FULL;
        enum SWSS_RC_IN_USE;
        enum SWSS_RC_NOT_IMPLEMENTED;
        enum SWSS_RC_FAILURE;
        enum SWSS_RC_INVALID_OBJECT_ID;
        enum SWSS_RC_INSUFFICIENT_RESOURCES;
        enum SWSS_RC_UNKNOWN;
      }
      description
        "Error code";
    }

    leaf operation {
      type string;
      description
        "Operation";
    }
  }

  grouping error-route-table-data {
    description
      "Grouping for error-route-table-data";

    leaf vrf-name {
      type string;
      description
        "Specify the vrf";
    }

    leaf prefix {
      type oc-inet:ip-prefix;
      description
        "IPv4 or IPv6 prefix";
    }

    leaf nexthop-group {
      type uint32;
      description
        "Nexthop group id, Nexthop Info is derived from group id";
    }

    leaf nexthop {
      type oc-inet:ip-address;
      description
        "Nexthop address";
    }

    leaf ifname {
      type oc-if:base-interface-ref;
      description
        "Interface name";
    }

  }

  grouping error-neighbor-table-data {
    description
      "Grouping for error-neighbor-table-data";

    leaf ipaddress {
      type oc-inet:ip-address;
      description
        "IP address";
    }

    leaf neigh{
      type oc-yang:mac-address;
      description
        "Mac address";
    }

    leaf ifname {
      type oc-if:base-interface-ref;
      description
        "Interface name";
    }

  }

  grouping error-ipmc-route-table-data {
    description
      "Grouping for error-ipmc-route-table-data";

    leaf vrf-name {
      type string;
      description
        "Specify the vrf";
    }

    leaf source-ip {
      type oc-inet:ip-address;
      description
        "Source IP";
    }

    leaf group-ip {
      type oc-inet:ip-address;
      description
        "Group IP";
    }

    leaf in-interface {
      type oc-if:base-interface-ref;
      description
        "Interface name";
    }

    leaf-list out-interfaces {
      type oc-if:base-interface-ref;
      description
        "Interface name";
    }

  }

  grouping error-route-table-top {
    description
      "Grouping for error-route-table";

    list error-route-table-entry {
      config false;
      key "prefix";
      description
        "Error Route Table Entry";

      leaf prefix {
        type leafref {
          path "../state/prefix";
        }
        description
          "";
      }

      container state {
        config false;
        description
          "State container for error-route-table entry";

        uses error-route-table-data;
        uses error-rc-opearation-codes;
      }
    }
  }

  grouping error-neighbor-table-top {
    description
      "Grouping for error-neighbor-table";

    list error-neighbor-table-entry {
      config false;
      key "ipaddress ifname";
      description
        "Error Neighbor Table Entry";

      leaf ipaddress {
        type leafref {
          path "../state/ipaddress";
        }
        description
          "";
      }

      leaf ifname {
        type leafref {
          path "../state/ifname";
        }
        description
          "";
      }

      container state {
        config false;
        description
          "State container for error-neighbor-table entry";

        uses error-neighbor-table-data;
        uses error-rc-opearation-codes;
      }
    }
  }

  grouping error-ipmc-route-table-top {
    description
      "Grouping for error-ipmc-route-table";

    list error-ipmc-route-table-entry {
      config false;
      key "source-ip group-ip";
      description
        "Error Ipmc Route Table Entry";

      leaf source-ip {
        type leafref {
          path "../state/source-ip";
        }
        description
          "";
      }

      leaf group-ip {
        type leafref {
          path "../state/group-ip";
        }
        description
          "";
      }

      container state {
        config false;
        description
          "State container for error-ipmc-route-table entry";

        uses error-ipmc-route-table-data;
        uses error-rc-opearation-codes;
      }
    }
  }

  grouping error-database-top {
    description
      "Top level grouping for error database";

    container error-database {
      description "error-database container";
      config false;

      container error-route-table {
        config false;
        description
          "Container for error-database route table";

        uses error-route-table-top;
      }

      container error-neighbor-table {
        config false;
        description
          "Container for error-database neighbor table";

        uses error-neighbor-table-top;
      }

      container error-ipmc-route-table {
        config false;
        description
          "Container for error-database ipmc-route-table";

        uses error-ipmc-route-table-top;
      }
    }
  }

  uses error-database-top;
}
