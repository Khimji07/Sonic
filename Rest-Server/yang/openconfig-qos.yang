module openconfig-qos {

  yang-version "1";

  // namespace
  namespace "http://openconfig.net/yang/qos";

  prefix "oc-qos";

  // import some basic types
  import openconfig-extensions { prefix oc-ext; }

  // include submodules
  include openconfig-qos-interfaces;
  include openconfig-qos-elements;


  // meta
  organization "OpenConfig working group";

  contact
    "OpenConfig working group
    www.openconfig.net";

  description
    "This module defines configuration and operational state data
    related to network quality-of-service.";

  oc-ext:openconfig-version "0.2.6";

  revision "2022-07-01" {
    description
      "Add WRED ECN counters";
    reference "0.2.6";
  }

  revision "2021-09-11" {
    description
      "Move PFC queue statistics to State clause ";
    reference "0.2.5";
  }

  revision "2021-06-01" {
    description
      "Add PFC configuration";
    reference "0.2.4";
  }

  revision "2019-11-28" {
    description
      "Fix xpaths in when statements";
    reference "0.2.3";
  }

  revision "2019-08-20" {
    description
      "Fix typo in classifiers container name";
    reference "0.2.2";
  }

  revision "2018-11-21" {
    description
      "Add OpenConfig module metadata extensions.";
    reference "0.2.1";
  }

  revision "2016-12-16" {
    description
      "Fix incorrect interface-ref placement";
    reference "0.2.0";
  }

  // OpenConfig specific extensions for module metadata.
  oc-ext:regexp-posix;
  oc-ext:catalog-organization "openconfig";
  oc-ext:origin "openconfig";

  // grouping statements
  grouping qos-config {
    description
      "Configuration data for global QoS";
  }

  grouping qos-state {
    description
      "Operational state data for global QoS";
  }

  grouping qos-top {
    description
      "Top-level grouping for QoS model";

    container qos {
      description
        "Top-level container for QoS data";

      container config {
        description
          "Configuration data for global QoS";

        uses qos-config;
      }

      container state {
        config false;
        description
          "Operational state data for global QoS";

        uses qos-config;
        uses qos-state;
      }

      uses qos-interfaces-top;
      uses qos-classifier-top;
      uses qos-forwarding-group-top;
      uses qos-queue-top;
      uses qos-scheduler-top;
      uses qos-pfc-watchdog-top;
      uses qos-watermark-top;
      uses qos-telemetry-watermark-top;
      uses qos-threshold-top;
      uses qos-threshold-breach-top;
      uses qos-wred-profile-top;
    }
  }

  // data definition statements

  uses qos-top;

  // augment statements

  // rpc statements
  // notification statements

}
