module openconfig-relay-agent-ext {

    yang-version "1";

    namespace "http://openconfig.net/yang/oc-relay-agent/extension";

    prefix "oc-relay-ext";

    import openconfig-extensions { prefix "oc-ext"; }
    import openconfig-relay-agent { prefix oc-relay; }

    // meta
    organization "OpenConfig working group";

    contact
        "OpenConfig working group
        netopenconfig@googlegroups.com";

    description
        "Model for managing DHCP_Relay configurations.";

    oc-ext:openconfig-version "0.1.1";

    revision "2020-03-11" {
        description
        "Initial release";
         reference "0.1.1";
    }

   // mode
   typedef mode {
       type enumeration {
             enum ENABLE {
             description "Enable field option";
             }
             enum DISABLE {
             description "Disable field option";
             }
       }
       description "To ENABLE/DISABLE a field";
   }
   

   // augment statements
    grouping "relay-agent-ext-config-top" {
                description "Augmented parameters for DHCP relay agent";
                leaf src-intf {
                        type string;
                        description "Configure the src-intf from which the packet should be relayed.";
                }
                
                leaf vrf {
                        type string;
                        description "Configure the VRF in which the server resides.";
                }

                leaf max-hop-count {
                        type uint32;
                        description "Configure the max hops the packet could be forwarded.";
                }

    }

    grouping "relay-agent-ext-v4-config" {
    		description "Params applicable to DHCPv4 only";

                leaf policy-action {
                       type enumeration {
                              enum DISCARD {
			      description "Relay agent discards the incoming packet";
			      }
                              enum APPEND {
			      description "Append set of relay options to the packet";
			      }
                              enum REPLACE {
			      description "Remove and add our set of relay options to the packet";
			      }
                        }
                        description "Configure the policy for handling of DHCPv4 relay options.";
                }

                leaf smart-relay {
                        type mode;
                        description "Enable/Disable smart relay mode on the given interface.";
                }
        }		

    grouping "relay-agent-ext-options" {
                description "Augmented parameters for DHCP relay agent information options";
                leaf vrf-select {
                        type mode;
                        description "Enable/Disable VRF selection option.";
                }
    }

    grouping "relay-agent-ext-v4-options" {
                description "Params applicable to DHCPv4 only agent information options.";
                leaf link-select {
                       type mode;
                        description "Enable/Disable link selection option.";
                       }
        }

    augment "/oc-relay:relay-agent/oc-relay:dhcpv6/oc-relay:interfaces/oc-relay:interface/oc-relay:config" {
            uses relay-agent-ext-config-top;       
            description "Configure the extended parameters";         
        }

    augment "/oc-relay:relay-agent/oc-relay:dhcpv6/oc-relay:interfaces/oc-relay:interface/oc-relay:state" {
            uses relay-agent-ext-config-top;     
            description "State of the extended parameters";
	    }


     augment "/oc-relay:relay-agent/oc-relay:dhcp/oc-relay:interfaces/oc-relay:interface/oc-relay:config" {
            uses relay-agent-ext-config-top;  
            uses relay-agent-ext-v4-config;  
            description "Configure the extended parameters, including the v4 specific parameters";        
        }

     augment "/oc-relay:relay-agent/oc-relay:dhcp/oc-relay:interfaces/oc-relay:interface/oc-relay:state" {
            uses relay-agent-ext-config-top;  
            uses relay-agent-ext-v4-config;  
            description "Configure the extended parameters, including the v4 specific parameters";        
        }
     augment "/oc-relay:relay-agent/oc-relay:dhcp/oc-relay:interfaces/oc-relay:interface/oc-relay:agent-information-option/oc-relay:config" {
            uses relay-agent-ext-options;
            uses relay-agent-ext-v4-options;
            description "Configure the extended parameters for agent information options, including the v4 specific options.";
        }

     augment "/oc-relay:relay-agent/oc-relay:dhcp/oc-relay:interfaces/oc-relay:interface/oc-relay:agent-information-option/oc-relay:state" {
            uses relay-agent-ext-options;
            uses relay-agent-ext-v4-options;
            description "State extended parameters for agent information options, including the v4 specific options.";
        }
     augment "/oc-relay:relay-agent/oc-relay:dhcpv6/oc-relay:interfaces/oc-relay:interface/oc-relay:options/oc-relay:config" {
            uses relay-agent-ext-options;
            description "Configure IPv6 specific extended parameters for agent information options.";
        }
     augment "/oc-relay:relay-agent/oc-relay:dhcpv6/oc-relay:interfaces/oc-relay:interface/oc-relay:options/oc-relay:state" {
            uses relay-agent-ext-options;
            description "State IPv6 specific extended parameters for agent information options.";
        }
    deviation /oc-relay:relay-agent/oc-relay:dhcp/oc-relay:config/oc-relay:enable-relay-agent {
      deviate not-supported;
    }

    deviation /oc-relay:relay-agent/oc-relay:dhcp/oc-relay:state/oc-relay:enable-relay-agent {
      deviate not-supported;
    }

    deviation /oc-relay:relay-agent/oc-relay:dhcp/oc-relay:agent-information-option/oc-relay:state/oc-relay:enable {
      deviate not-supported;
    }

    deviation /oc-relay:relay-agent/oc-relay:dhcp/oc-relay:agent-information-option/oc-relay:config/oc-relay:enable {
      deviate not-supported;
    }

    deviation /oc-relay:relay-agent/oc-relay:dhcp/oc-relay:interfaces/oc-relay:interface/oc-relay:config/oc-relay:enable {
      deviate not-supported;
    }

    deviation /oc-relay:relay-agent/oc-relay:dhcp/oc-relay:interfaces/oc-relay:interface/oc-relay:state/oc-relay:enable {
      deviate not-supported;
    }

    deviation /oc-relay:relay-agent/oc-relay:dhcp/oc-relay:interfaces/oc-relay:interface/oc-relay:interface-ref/oc-relay:state/oc-relay:subinterface {
      deviate not-supported;
    }

    deviation /oc-relay:relay-agent/oc-relay:dhcp/oc-relay:interfaces/oc-relay:interface/oc-relay:interface-ref/oc-relay:state/oc-relay:interface {
      deviate not-supported;
    }


    deviation /oc-relay:relay-agent/oc-relay:dhcp/oc-relay:interfaces/oc-relay:interface/oc-relay:interface-ref/oc-relay:config/oc-relay:interface {
      deviate not-supported;
    }

    deviation /oc-relay:relay-agent/oc-relay:dhcp/oc-relay:interfaces/oc-relay:interface/oc-relay:interface-ref/oc-relay:config/oc-relay:subinterface {
      deviate not-supported;
    }

    deviation /oc-relay:relay-agent/oc-relay:dhcp/oc-relay:interfaces/oc-relay:interface/oc-relay:agent-information-option/oc-relay:config/oc-relay:remote-id {
      deviate not-supported;
    }

    deviation /oc-relay:relay-agent/oc-relay:dhcp/oc-relay:interfaces/oc-relay:interface/oc-relay:agent-information-option/oc-relay:config/oc-relay:enable {
      deviate not-supported;
    }

    deviation /oc-relay:relay-agent/oc-relay:dhcp/oc-relay:interfaces/oc-relay:interface/oc-relay:agent-information-option/oc-relay:state/oc-relay:enable {
      deviate not-supported;
    }

    deviation /oc-relay:relay-agent/oc-relay:dhcp/oc-relay:interfaces/oc-relay:interface/oc-relay:agent-information-option/oc-relay:state/oc-relay:remote-id {
        deviate not-supported;
    }

    deviation /oc-relay:relay-agent/oc-relay:dhcp/oc-relay:interfaces/oc-relay:interface/oc-relay:agent-information-option/oc-relay:state/oc-relay:sent-circuit-id {
        deviate not-supported;
    }

    deviation /oc-relay:relay-agent/oc-relay:dhcp/oc-relay:interfaces/oc-relay:interface/oc-relay:agent-information-option/oc-relay:state/oc-relay:sent-remote-id {
        deviate not-supported;
    }

    deviation /oc-relay:relay-agent/oc-relay:dhcpv6/oc-relay:config/oc-relay:enable-relay-agent {
        deviate not-supported;
    }

    deviation /oc-relay:relay-agent/oc-relay:dhcpv6/oc-relay:state/oc-relay:enable-relay-agent {
        deviate not-supported;
    }

    deviation /oc-relay:relay-agent/oc-relay:dhcpv6/oc-relay:options/oc-relay:config/oc-relay:enable-interface-id {
        deviate not-supported;
    }

    deviation /oc-relay:relay-agent/oc-relay:dhcpv6/oc-relay:options/oc-relay:config/oc-relay:enable-remote-id {
        deviate not-supported;
    }

    deviation /oc-relay:relay-agent/oc-relay:dhcpv6/oc-relay:options/oc-relay:state/oc-relay:enable-interface-id {
        deviate not-supported;
    }

    deviation /oc-relay:relay-agent/oc-relay:dhcpv6/oc-relay:options/oc-relay:state/oc-relay:enable-remote-id {
        deviate not-supported;
    }

    deviation /oc-relay:relay-agent/oc-relay:dhcpv6/oc-relay:interfaces/oc-relay:interface/oc-relay:config/oc-relay:enable {
        deviate not-supported;
    }

    deviation /oc-relay:relay-agent/oc-relay:dhcpv6/oc-relay:interfaces/oc-relay:interface/oc-relay:state/oc-relay:enable {
        deviate not-supported;
    }

    deviation /oc-relay:relay-agent/oc-relay:dhcpv6/oc-relay:interfaces/oc-relay:interface/oc-relay:interface-ref/oc-relay:state/oc-relay:subinterface {
        deviate not-supported;
    }

    deviation /oc-relay:relay-agent/oc-relay:dhcpv6/oc-relay:interfaces/oc-relay:interface/oc-relay:interface-ref/oc-relay:state/oc-relay:interface {
      deviate not-supported;
    }

    deviation /oc-relay:relay-agent/oc-relay:dhcpv6/oc-relay:interfaces/oc-relay:interface/oc-relay:interface-ref/oc-relay:config/oc-relay:interface {
      deviate not-supported;
    }

    deviation /oc-relay:relay-agent/oc-relay:dhcpv6/oc-relay:interfaces/oc-relay:interface/oc-relay:interface-ref/oc-relay:config/oc-relay:subinterface {
        deviate not-supported;
    }

    deviation /oc-relay:relay-agent/oc-relay:dhcpv6/oc-relay:interfaces/oc-relay:interface/oc-relay:options/oc-relay:config/oc-relay:interface-id {
        deviate not-supported;
    }

    deviation /oc-relay:relay-agent/oc-relay:dhcpv6/oc-relay:interfaces/oc-relay:interface/oc-relay:options/oc-relay:config/oc-relay:enable-interface-id {
        deviate not-supported;
    }

    deviation /oc-relay:relay-agent/oc-relay:dhcpv6/oc-relay:interfaces/oc-relay:interface/oc-relay:options/oc-relay:config/oc-relay:enable-remote-id {
        deviate not-supported;
    }

    deviation /oc-relay:relay-agent/oc-relay:dhcpv6/oc-relay:interfaces/oc-relay:interface/oc-relay:options/oc-relay:config/oc-relay:remote-id {
        deviate not-supported;
    }

    deviation /oc-relay:relay-agent/oc-relay:dhcpv6/oc-relay:interfaces/oc-relay:interface/oc-relay:options/oc-relay:state/oc-relay:sent-interface-id {
        deviate not-supported;
    }

    deviation /oc-relay:relay-agent/oc-relay:dhcpv6/oc-relay:interfaces/oc-relay:interface/oc-relay:options/oc-relay:state/oc-relay:sent-remote-id {
        deviate not-supported;
    }

    deviation /oc-relay:relay-agent/oc-relay:dhcpv6/oc-relay:interfaces/oc-relay:interface/oc-relay:options/oc-relay:state/oc-relay:interface-id {
        deviate not-supported;
    }

    deviation /oc-relay:relay-agent/oc-relay:dhcpv6/oc-relay:interfaces/oc-relay:interface/oc-relay:options/oc-relay:state/oc-relay:enable-interface-id {
        deviate not-supported;
    }

    deviation /oc-relay:relay-agent/oc-relay:dhcpv6/oc-relay:interfaces/oc-relay:interface/oc-relay:options/oc-relay:state/oc-relay:enable-remote-id {
        deviate not-supported;
    }

    deviation /oc-relay:relay-agent/oc-relay:dhcpv6/oc-relay:interfaces/oc-relay:interface/oc-relay:options/oc-relay:state/oc-relay:remote-id {
        deviate not-supported;
    }

}
