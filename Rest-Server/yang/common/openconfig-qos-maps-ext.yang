module openconfig-qos-maps-ext {

    yang-version "1";

    // namespace
    namespace "http://openconfig.net/yang/qos-maps/extension";

    prefix "oc-qos-maps-ext";

    import openconfig-qos { prefix oc-qos; }
    import openconfig-extensions { prefix oc-ext; }
  
    organization "Dell";

    contact
      "Dell";

    description
      "This module defines YANG model for network quality-of-service maps extension.";

    oc-ext:openconfig-version "0.1.0";

    revision "2020-04-30" {
      description
        "Initial version";
      reference "0.1.0";
    }

    identity PACKET_COLOR {
        description
            "Base identity to describe packet colors.";
    }

    identity GREEN {
        base PACKET_COLOR;
        description
            "Packet color GREEN.";
    }
    
    identity YELLOW {
        base PACKET_COLOR;
        description
            "Packet color YELLOW.";
    }
    
    identity RED {
        base PACKET_COLOR;
        description
            "Packet color RED.";
    }
    
    grouping qos-maps-ext-dscp-map-entry-config {
	    description "DSCP map entry config";
		leaf dscp {
            type uint8 {
                range 0..63;
            }
            description
                "The 6-bit DSCP (differentiated services code point) value in the IP packet header.";
            reference
                "RFC 2474 - Definition of the Differentiated Services Field
                 (DS Field) in the IPv4 and IPv6 Headers";
		}

		leaf fwd-group {
			type leafref {
				path "../../../../../../oc-qos:forwarding-groups/oc-qos:forwarding-group/oc-qos:config/oc-qos:name";
			}
            mandatory true;
			description
				"Name of forwarding group map.";
		}

        leaf color {
            type identityref {
                base PACKET_COLOR;
            }
            default GREEN;
            description
                "Sets the color of packet.";
        }
	}
	
    grouping qos-maps-ext-dscp-map-entry-state {
	    description "Operational state data for DSCP map entry";
	}

	grouping qos-maps-ext-dscp-map-entries-top {
		description
			"Top-level grouping for DSCP map entries";

		container dscp-map-entries {
    		description
	     	    "Container for DSCP map entries";

		    list dscp-map-entry {
			    key "dscp";
				
    		    description
	     	        "List of DSCP map entries";

				leaf dscp {
				    type leafref {
					    path ../config/dscp;
					}
                    description
                        "Reference to DSCP map entry key";
                }
				
				container config {
                    description
                        "Configuration data for DSCP map entries";

                    uses qos-maps-ext-dscp-map-entry-config;
				}
				
				container state {
                    config false;
                    description
                        "Operational data for DSCP map entries";
				    uses qos-maps-ext-dscp-map-entry-config;
				    uses qos-maps-ext-dscp-map-entry-state;
				}
			}
		}
	}

    grouping qos-maps-ext-forwarding-group-dscp-map-entry-config {
	    description "Fwd-group DSCP map entry config";
		leaf fwd-group {
			type leafref {
				path "../../../../../../oc-qos:forwarding-groups/oc-qos:forwarding-group/oc-qos:config/oc-qos:name";
			}
            mandatory true;
			description
				"Name of forwarding group map.";
		}

        leaf color {
            type identityref {
                base PACKET_COLOR;
            }
            default GREEN;
            description
                "Sets the color of packet.";
        }

		leaf dscp {
            type uint8 {
                range 0..63;
            }
            description
                "The 6-bit DSCP (differentiated services code point) value in the IP packet header.";
            reference
                "RFC 2474 - Definition of the Differentiated Services Field
                 (DS Field) in the IPv4 and IPv6 Headers";
		}

	}
	
    grouping qos-maps-ext-forwarding-group-dscp-map-entry-state {
	    description "Operational state data for Fwd-group DSCP map entry";
	}

	grouping qos-maps-ext-forwarding-group-dscp-map-entries-top {
		description
			"Top-level grouping for Fwd-group to DSCP map entries";

		container forwarding-group-dscp-map-entries {
    		description
	     	    "Container for Fwd-grup to DSCP map entries";

		    list forwarding-group-dscp-map-entry {
			    key "fwd-group";
				
    		    description
	     	        "List of Fwd-group to DSCP map entries";

				leaf fwd-group {
				    type leafref {
					    path ../config/fwd-group;
					}
                    description
                        "Reference to fwd-group map entry key";
                }
				
				container config {
                    description
                        "Configuration data for Fwd-group to DSCP map entries";

                    uses qos-maps-ext-forwarding-group-dscp-map-entry-config;
				}
				
				container state {
                    config false;
                    description
                        "Operational data for Fwd-group to DSCP map entries";
				    uses qos-maps-ext-forwarding-group-dscp-map-entry-config;
				    uses qos-maps-ext-forwarding-group-dscp-map-entry-state;
				}
			}
		}
	}
 
    grouping qos-maps-ext-dscp-map-config {
		description
			"Configuration data for DSCP map";

		leaf name {
			type string;
			description
				"Name of the DSCP map";
		}

	}
    grouping qos-maps-ext-dscp-map-state {
		description
			"Operational data for DSCP map";
	}

	grouping qos-maps-ext-dscp-maps-top {   
		description
			" Top-level grouping for DSCP maps data";

		container dscp-maps {
			description
				"Enclosing container for list of dscp maps";

			list dscp-map {
				key "name";
    		    description
	     	        "List of DSCP maps";
                leaf name {
                  type leafref {
                    path "../config/name";
                  }
                  description
                    "Reference to the name of the dscp map.";
                }
				
                container config {
                    description
                        "Configuration parameters relating to dscp map.";
					uses qos-maps-ext-dscp-map-config;
				}

				container state {
 					config false;
                    description
                        "Operational parameters relating to dscp map.";
					uses qos-maps-ext-dscp-map-config;
					uses qos-maps-ext-dscp-map-state;
				}
                uses qos-maps-ext-dscp-map-entries-top;
			}
		}
	}

    grouping qos-maps-ext-forwarding-group-dscp-map-config {
		description
			"Configuration data for Fwd-group DSCP map";

		leaf name {
			type string;
			description
				"Name of the fwd-group DSCP map";
		}

	}
    grouping qos-maps-ext-forwarding-group-dscp-map-state {
		description
			"Operational data for fwd-group DSCP map";
	}

	grouping qos-maps-ext-forwarding-group-dscp-maps-top {   
		description
			" Top-level grouping for fwd-group DSCP maps data";

		container forwarding-group-dscp-maps {
			description
				"Enclosing container for list of fwd-group dscp maps";

			list forwarding-group-dscp-map {
				key "name";
    		    description
	     	        "List of Fwd-group DSCP maps";
                leaf name {
                  type leafref {
                    path "../config/name";
                  }
                  description
                    "Reference to the name of the fwd-group dscp map.";
                }
				
                container config {
                    description
                        "Configuration parameters relating to fwd-group dscp map.";
					uses qos-maps-ext-forwarding-group-dscp-map-config;
				}

				container state {
 					config false;
                    description
                        "Operational parameters relating to dscp map.";
					uses qos-maps-ext-forwarding-group-dscp-map-config;
					uses qos-maps-ext-forwarding-group-dscp-map-state;
				}
                uses qos-maps-ext-forwarding-group-dscp-map-entries-top;
			}
		}
	}

    grouping qos-maps-ext-dot1p-map-entry-config {
	    description "DOT1P to Forwarding group map entry config";
		leaf dot1p {
            type uint8 {
                range 0..7;
            }
            description
                "3-bit class-of-service value in the
                 Ethernet packet header for 802.1Q VLAN-tagged packets,
                 also known as PCP (priority code point).";
            reference
                 "IEEE 802.1Q-2014 - IEEE Standard for Local and metropolitan
                  area networks--Bridges and Bridged Networks";
		}

		leaf fwd-group {
			type leafref {
				path "../../../../../../oc-qos:forwarding-groups/oc-qos:forwarding-group/oc-qos:config/oc-qos:name";
			}
            mandatory true;
			description
				"Name of forwarding group.";
		}

        leaf color {
            type identityref {
                base PACKET_COLOR;
            }
            default GREEN;
            description
                "Sets the color of packet.";
        }
	}
	
    grouping qos-maps-ext-dot1p-map-entry-state {
	    description "Operational data for DOT1P to Forwarding group map entry.";
	}

	grouping qos-maps-ext-dot1p-map-entries-top {
		description
			"Top-level grouping for DOT1P map entries";

		container dot1p-map-entries {
        
    		description
	     	    "Container for DOT1P map entries";
		    list dot1p-map-entry {
			    key "dot1p";
				description
	     	        "List of DOT1P map entries";

				leaf dot1p {
				    type leafref {
					    path ../config/dot1p;
					}
                    description
                        "Reference to DOT1P map entry key";
				}
				
				container config {
                    description
                        "Configuration data for DOT1P map entries";
				    uses qos-maps-ext-dot1p-map-entry-config;
				}
				
				container state {
                    config false;
                    description
                        "Operational data for DOT1P map entries";
				    uses qos-maps-ext-dot1p-map-entry-config;
				    uses qos-maps-ext-dot1p-map-entry-state;
				}
			}
		}
	}

    grouping qos-maps-ext-forwarding-group-dot1p-map-entry-config {
	    description "Fwd-group DOT1P map entry config";
		leaf fwd-group {
			type leafref {
				path "../../../../../../oc-qos:forwarding-groups/oc-qos:forwarding-group/oc-qos:config/oc-qos:name";
			}
            mandatory true;
			description
				"Name of forwarding group map.";
		}

        leaf color {
            type identityref {
                base PACKET_COLOR;
            }
            default GREEN;
            description
                "Sets the color of packet.";
        }

		leaf dot1p {
            type uint8 {
                range 0..7;
            }
            description
                "3-bit class-of-service value in the
                 Ethernet packet header for 802.1Q VLAN-tagged packets,
                 also known as PCP (priority code point).";
            reference
                 "IEEE 802.1Q-2014 - IEEE Standard for Local and metropolitan
                  area networks--Bridges and Bridged Networks";
		}
	}
	
    grouping qos-maps-ext-forwarding-group-dot1p-map-entry-state {
	    description "Operational state data for Fwd-group DOT1P map entry";
	}

	grouping qos-maps-ext-forwarding-group-dot1p-map-entries-top {
		description
			"Top-level grouping for Fwd-group to DOT1P map entries";

		container forwarding-group-dot1p-map-entries {
    		description
	     	    "Container for Fwd-grup to DOT1P map entries";

		    list forwarding-group-dot1p-map-entry {
			    key "fwd-group";
				
    		    description
	     	        "List of Fwd-group to DOT1P map entries";

				leaf fwd-group {
				    type leafref {
					    path ../config/fwd-group;
					}
                    description
                        "Reference to fwd-group map entry key";
                }
				
				container config {
                    description
                        "Configuration data for Fwd-group to DOT1P map entries";

                    uses qos-maps-ext-forwarding-group-dot1p-map-entry-config;
				}
				
				container state {
                    config false;
                    description
                        "Operational data for Fwd-group to DOT1P map entries";
				    uses qos-maps-ext-forwarding-group-dot1p-map-entry-config;
				    uses qos-maps-ext-forwarding-group-dot1p-map-entry-state;
				}
			}
		}
	}
 
 
    grouping qos-maps-ext-dot1p-map-config {
		description
			"Configuration data for DOT1P to Forwarding Group map";

		leaf name {
			type string;
			description
				"Name of the forwarding group";
		}
	}

    grouping qos-maps-ext-dot1p-map-state {
		description
			"Operational data for DOT1P to Forwarding Group map";
	}

	grouping qos-maps-ext-dot1p-maps-top {   
		description
			" Top-level grouping for DOT1P to forwarding group maps data";

		container dot1p-maps {
			description
				"Enclosing container for list of dot1p to forwarding group maps";

			list dot1p-map {
				key "name";
    		    description
	     	        "List of DSCP maps";
                leaf name {
                  type leafref {
                    path "../config/name";
                  }
                  description
                    "Reference to the name of the dot1p to forwading group map name.";
                }
				
                container config {
                    description
                        "Configuration parameters relating to dot1p to forwading group map.";
					uses qos-maps-ext-dot1p-map-config;
				}

				container state {
 					config false;
                    description
                        "Operational parameters relating to dot1p to forwading group map";
					uses qos-maps-ext-dot1p-map-config;
					uses qos-maps-ext-dot1p-map-state;
				}
                uses qos-maps-ext-dot1p-map-entries-top;
			}
		}
	}

    grouping qos-maps-ext-forwarding-group-dot1p-map-config {
		description
			"Configuration data for Fwd-group DOT1P map";

		leaf name {
			type string;
			description
				"Name of the fwd-group DOT1P map";
		}

	}
    grouping qos-maps-ext-forwarding-group-dot1p-map-state {
		description
			"Operational data for fwd-group DOT1P map";
	}

	grouping qos-maps-ext-forwarding-group-dot1p-maps-top {   
		description
			" Top-level grouping for fwd-group DOT1P maps data";

		container forwarding-group-dot1p-maps {
			description
				"Enclosing container for list of fwd-group dot1p maps";

			list forwarding-group-dot1p-map {
				key "name";
    		    description
	     	        "List of Fwd-group DOT1P maps";
                leaf name {
                  type leafref {
                    path "../config/name";
                  }
                  description
                    "Reference to the name of the fwd-group dot1p map.";
                }
				
                container config {
                    description
                        "Configuration parameters relating to fwd-group dot1p map.";
					uses qos-maps-ext-forwarding-group-dot1p-map-config;
				}

				container state {
 					config false;
                    description
                        "Operational parameters relating to dot1p map.";
					uses qos-maps-ext-forwarding-group-dot1p-map-config;
					uses qos-maps-ext-forwarding-group-dot1p-map-state;
				}
                uses qos-maps-ext-forwarding-group-dot1p-map-entries-top;
			}
		}
	}

    grouping qos-maps-ext-forwarding-group-queue-map-entry-config {
	    description
            "Forwarding group to queue index map entry config";

		leaf fwd-group {
			type leafref {
				path "../../../../../../oc-qos:forwarding-groups/oc-qos:forwarding-group/oc-qos:config/oc-qos:name";
			}
			description
				"Name of forwarding group.";
		}

		leaf output-queue-index {
            type uint8 {
                range 0..7;
            }
            mandatory true;
            description
                "Output queue index on interfaces.";
		}

	}
	
    grouping qos-maps-ext-forwarding-group-queue-map-entry-state {
	    description
            "Operational date for Forwarding group to queue index map entry";
	}

	grouping qos-maps-ext-forwarding-group-queue-map-entries-top {
		description
			"Top-level grouping for Forwarding Group to queue index map entries";

		container forwarding-group-queue-map-entries {
    		description
	     	    "Container for Forwarding Group to queue index map entries";
		    list forwarding-group-queue-map-entry {
			    key "fwd-group";
				
    		    description
	     	        "List of Forwarding Group to queue index map entries";
				leaf fwd-group {
				    type leafref {
					    path ../config/fwd-group;
					}
                    description
                        "Reference to Forwarding Group to queue index map entry key";
				}
				
				container config {
                    description
                        "Configuration data for Forwarding Group to queue index map entries";
				    uses qos-maps-ext-forwarding-group-queue-map-entry-config;
				}
				
				container state {
                    config false;
                    description
                        "Operational data for Forwarding Group to queue index map entries";
				    uses qos-maps-ext-forwarding-group-queue-map-entry-config;
				    uses qos-maps-ext-forwarding-group-queue-map-entry-state;
				}
			}
		}
	}
 
    grouping qos-maps-ext-forwarding-group-queue-map-config {
		description
			"Configuration data for Forwarding Group to queue index map";

		leaf name {
			type string;
			description
				"Name of the forwarding group to queue map";
		}

	}

    grouping qos-maps-ext-forwarding-group-queue-map-state {
		description
			"Operational data for Forwarding Group to queue index map";
	}
	grouping qos-maps-ext-forwarding-group-queue-maps-top {   
		description
			" Top-level grouping for Forwarding group to queue maps data";

		container forwarding-group-queue-maps {
			description
				"Enclosing container for list of forwarding group to queue maps";

			list forwarding-group-queue-map {
				key "name";
    		    description
	     	        "List of forwading group to queue maps";
                leaf name {
                  type leafref {
                    path "../config/name";
                  }
                  description
                    "Reference to the name of the forwading group to queues map.";
                }
				
                container config {
                    description
                        "Configuration parameters relating to forwading groups to queue map.";
					uses qos-maps-ext-forwarding-group-queue-map-config;
				}

				container state {
 					config false;
                    description
                        "Operational parameters relating to forwading group to queue map.";
					uses qos-maps-ext-forwarding-group-queue-map-config;
					uses qos-maps-ext-forwarding-group-queue-map-state;
				}
                uses qos-maps-ext-forwarding-group-queue-map-entries-top;
			}
		}
	}

    grouping qos-maps-ext-forwarding-group-priority-group-map-entry-config {
	    description
            "Forwarding group to priority group index map entry config";

		leaf fwd-group {
			type leafref {
				path "../../../../../../oc-qos:forwarding-groups/oc-qos:forwarding-group/oc-qos:config/oc-qos:name";
			}
			description
				"Name of forwarding group.";
		}

		leaf priority-group-index {
            type uint8 {
                range 0..7;
            }
            mandatory true;
            description
                "priority group index on interfaces.";
		}
	}
	
    grouping qos-maps-ext-forwarding-group-priority-group-map-entry-state {
	    description
            "Operational data for Forwarding group to priority group index map entry";
    }

	grouping qos-maps-ext-forwarding-group-priority-group-map-entries-top {
		description
			"Top-level grouping for Forwarding Group to priority group index map entries";

		container forwarding-group-priority-group-map-entries {
    		description
	     	    "Container for Forwarding Group to priority group index map entries";
		    list forwarding-group-priority-group-map-entry {
			    key "fwd-group";
				
    		    description
	     	        "List of Forwarding Group map entries";
				leaf fwd-group {
				    type leafref {
					    path ../config/fwd-group;
					}
                    description
                        "Reference to Forwarding Group map entry key";
				}
				
				container config {
                    description
                        "Configuration data for Forwarding Group map entries";
				    uses qos-maps-ext-forwarding-group-priority-group-map-entry-config;
				}
				
				container state {
                    config false;
                    description
                        "Operational data for Forwarding Group map entries";
				    uses qos-maps-ext-forwarding-group-priority-group-map-entry-config;
				    uses qos-maps-ext-forwarding-group-priority-group-map-entry-state;
				}
			}
		}
	}
 
    grouping qos-maps-ext-forwarding-group-priority-group-map-config {
		description
			"Configuration data for Forwarding Group to priority group index map";

		leaf name {
			type string;
			description
				"Name of the forwarding group to priority group map";
		}

	}
 
    grouping qos-maps-ext-forwarding-group-priority-group-map-state {
		description
			"Operational data for Forwarding Group to priority group index map";
	}


	grouping qos-maps-ext-forwarding-group-priority-group-maps-top {   
		description
			" Top-level grouping for Forwarding group to priority group maps data";

		container forwarding-group-priority-group-maps {
			description
				"Enclosing container for list of forwarding group to priority group maps";

			list forwarding-group-priority-group-map {
				key "name";
    		    description
	     	        "List of forwarding group to priority group maps";
                leaf name {
                  type leafref {
                    path "../config/name";
                  }
                  description
                    "Reference to the name of the forwading group to priority group map.";
                }
				
                container config {
                    description
                        "Configuration parameters relating to forwading groups to queue map.";
					uses qos-maps-ext-forwarding-group-priority-group-map-config;
				}

				container state {
 					config false;
                    description
                        "Operational parameters relating to forwading group to priority group map.";
					uses qos-maps-ext-forwarding-group-priority-group-map-config;
					uses qos-maps-ext-forwarding-group-priority-group-map-state;
				}
                uses qos-maps-ext-forwarding-group-priority-group-map-entries-top;
			}
		}
	}

    grouping qos-maps-ext-pfc-priority-queue-map-entry-config {
	    description
            "PFC priroity to queue index map entry config";
     	leaf dot1p {
            type uint8 {
                range 0..7;
            }
            description
                "3-bit class-of-service value in the
                 Ethernet packet header for 802.1Q VLAN-tagged packets,
                 also known as PCP (priority code point).";
            reference
                 "IEEE 802.1Q-2014 - IEEE Standard for Local and metropolitan
                  area networks--Bridges and Bridged Networks";
		}

		leaf output-queue-index {
            type uint8 {
                range 0..7;
            }
            mandatory true;
            description
                "Output queue index on interfaces.";
		}
	}
	
    grouping qos-maps-ext-pfc-priority-queue-map-entry-state {
	    description
            "Operational date for PFC priroity to queue index map entry";
    }
	grouping qos-maps-ext-pfc-priority-queue-map-entries-top {
		description
			"Top-level grouping for PFC priroity to queue index map entries";

		container pfc-priority-queue-map-entries {
    		description
	     	    "Container for PFC priroity to queue index map entries";
		    list pfc-priority-queue-map-entry {
			    key "dot1p";
				
    		    description
	     	        "List of PFC priroity to queue index map entries";
				leaf dot1p {
				    type leafref {
					    path ../config/dot1p;
					}
                    description
                        "Reference to PFC priroity to queue index map entry key";
				}
				
				container config {
                    description
                        "Configuration data for PFC priroity to queue index map entries";
				    uses qos-maps-ext-pfc-priority-queue-map-entry-config;
				}
				
				container state {
                    config false;
                    description
                        "Operational data for PFC priroity to queue index map entries";
				    uses qos-maps-ext-pfc-priority-queue-map-entry-config;
				    uses qos-maps-ext-pfc-priority-queue-map-entry-state;
				}
			}
		}
	}
 
    grouping qos-maps-ext-pfc-priority-queue-map-config {
		description
			"Configuration data for PFC priority to queue index map";

		leaf name {
			type string;
			description
				"Name of the PFC priority to queue map";
		}

	}
 
    grouping qos-maps-ext-pfc-priority-queue-map-state {
		description
			"Operational data for PFC priority to queue index map";
	}

	grouping qos-maps-ext-pfc-priority-queue-maps-top {   
		description
			" Top-level grouping for PFC priority to queue maps data";

		container pfc-priority-queue-maps {
			description
				"Enclosing container for list of PFC priority to queue maps";

			list pfc-priority-queue-map {
				key "name";
    		    description
	     	        "List of PFC priority to queue maps";
                leaf name {
                  type leafref {
                    path "../config/name";
                  }
                  description
                    "Reference to the name of the PFC priority to queues map.";
                }
				
                container config {
                    description
                        "Configuration parameters relating to PFC priority to queue map.";
		  			uses qos-maps-ext-pfc-priority-queue-map-config;
				}

				container state {
 					config false;
                    description
                        "Operational parameters relating to PFC priority to queue map.";
					uses qos-maps-ext-pfc-priority-queue-map-config;
					uses qos-maps-ext-pfc-priority-queue-map-state;
				}
                uses qos-maps-ext-pfc-priority-queue-map-entries-top;
			}
		}
	}

	grouping qos-maps-ext-pfc-priority-priority-group-map-entry-config {
		description
        		"PFC priroity to priority group index map entry config";
     		leaf dot1p {
            		type uint8 {
                		range 0..7;
        		}
            		description
                		"3-bit class-of-service value in the
                 		Ethernet packet header for 802.1Q VLAN-tagged packets,
                 		also known as PCP (priority code point).";
            		reference
                 		"IEEE 802.1Q-2014 - IEEE Standard for Local and metropolitan
                  		area networks--Bridges and Bridged Networks";
		}

		leaf priority-group-index {
        		type uint8 {
                		range 0..7;
            		}
            		mandatory true;
            		description
                		"priority group index on interfaces.";
		}
	}
	
	grouping qos-maps-ext-pfc-priority-priority-group-map-entry-state {
	    description
        	    "Operational date for PFC priroity to priority group index map entry";
	}

	grouping qos-maps-ext-pfc-priority-priority-group-map-entries-top {
		description
			"Top-level grouping for PFC priroity to priority group index map entries";

		container pfc-priority-priority-group-map-entries {
    			description
	     	    		"Container for PFC priroity to priority group index map entries";
				
		    	list pfc-priority-priority-group-map-entry {
				key "dot1p";
				
    		    		description
	     	        		"List of PFC priroity to priority group index map entries";
				leaf dot1p {
				    	type leafref {
					    path ../config/dot1p;
					}
                    			description
                        			"Reference to PFC priroity to priority group index map entry key";
				}
				
				container config {
                			description
                        			"Configuration data for PFC priroity to priority group index map entries";
				    	uses qos-maps-ext-pfc-priority-priority-group-map-entry-config;
				}
				
				container state {
                    			config false;
                    			description
                        			"Operational data for PFC priroity to queue index map entries";
				    	uses qos-maps-ext-pfc-priority-priority-group-map-entry-config;
				    	uses qos-maps-ext-pfc-priority-priority-group-map-entry-state;
				}
			}
		}
	}
 
	grouping qos-maps-ext-pfc-priority-priority-group-map-config {
		description
			"Configuration data for PFC priority to priority group index map";

		leaf name {
			type string;
			description
				"Name of the PFC priority to priority group map";
		}

	}
 
    	grouping qos-maps-ext-pfc-priority-priority-group-map-state {
		description
			"Operational data for PFC priority to priority group index map";
	}

	grouping qos-maps-ext-pfc-priority-priority-group-maps-top {   
		description
			" Top-level grouping for PFC priority to Priority Group maps data";

		container pfc-priority-priority-group-maps {
			description
				"Enclosing container for list of PFC priority to priority group maps";

			list pfc-priority-priority-group-map {
				key "name";
    		    			description
	     	        		"List of PFC priority to priority group maps";
                		leaf name {
                  			type leafref {
                    				path "../config/name";
                  			}
                  			description
                    				"Reference to the name of the PFC priority to priority group map.";
                		}
				
                		container config {
                    			description
                        			"Configuration parameters relating to PFC priority to priority group map.";
		  			uses qos-maps-ext-pfc-priority-priority-group-map-config;
				}

				container state {
 					config false;
                    			description
                        			"Operational parameters relating to PFC priority to priority group map.";
					uses qos-maps-ext-pfc-priority-priority-group-map-config;
					uses qos-maps-ext-pfc-priority-priority-group-map-state;
				}
                		uses qos-maps-ext-pfc-priority-priority-group-map-entries-top;
			}
		}
	}

   	grouping qos-maps-ext-interface-maps-config {
		description
			"Configuration data for the maps with the interface";

		leaf dscp-to-forwarding-group {
			type leafref {
				// current loc:
				// /qos/interfaces/interface/interface-maps/config/dscp-to-forwarding-group
				path "../../../../../dscp-maps/dscp-map/config/name";
			}
    		description
	    		"Reference to DSCP to forwarding group map associated with the interface";
		}

		leaf dot1p-to-forwarding-group {
			type leafref {
				// current loc:
				// /qos/interfaces/interface/interface-maps/config/dot1p-to-forwarding-group
				path "../../../../../dot1p-maps/dot1p-map/config/name";
			}
    		description
	    		"Reference to DOT1P to forwarding group map associated with the interface";
		}

        leaf forwarding-group-to-dscp {
			type leafref {
				// current loc:
				// /qos/interfaces/interface/interface-maps/config/forwarding-group-to-dscp
				path "../../../../../forwarding-group-dscp-maps/forwarding-group-dscp-map/config/name";
			}
    		description
	    		"Reference to forwarding group to dscp map associated with the interface";
		}

        leaf forwarding-group-to-dot1p {
			type leafref {
				// current loc:
				// /qos/interfaces/interface/interface-maps/config/forwarding-group-to-dot1p
				path "../../../../../forwarding-group-dot1p-maps/forwarding-group-dot1p-map/config/name";
			}
    		description
	    		"Reference to forwarding group to dot1p map associated with the interface";
		}

        leaf forwarding-group-to-queue {
			type leafref {
				// current loc:
				// /qos/interfaces/interface/interface-maps/config/forwarding-group-to-queue
				path "../../../../../forwarding-group-queue-maps/forwarding-group-queue-map/config/name";
			}
    		description
	    		"Reference to forwarding group to queue map associated with the interface";
		}

        leaf pfc-priority-to-queue {
			type leafref {
				// current loc:
				// /qos/interfaces/interface/interface-maps/config/dscp-to-forwarding-group
				path "../../../../../pfc-priority-queue-maps/pfc-priority-queue-map/config/name";
			}
    		description
	    		"Reference to PFC priority to queue map associated with the interface";
		}

        leaf forwarding-group-to-priority-group {
			type leafref {
				// current loc:
				// /qos/interfaces/interface/interface-maps/config/dscp-to-forwarding-group
				path "../../../../../forwarding-group-priority-group-maps/forwarding-group-priority-group-map/config/name";
			}
    		description
	    		"Reference to Forwading group to priority group map associated with the interface";
		}
		leaf pfc-priority-to-priority-group {
			type leafref {
				// current loc:
				// /qos/interfaces/interface/interface-maps/config/dscp-to-forwarding-group
				path "../../../../../pfc-priority-priority-group-maps/pfc-priority-priority-group-map/config/name";
			}
    		description
	    		"Reference to PFC priority to priority group map associated with the interface";
		}

	}

   	grouping qos-maps-ext-interface-maps-state {
		description
			"Operational data for the maps with the interface";
    }

    grouping qos-maps-ext-interface-maps-top {
        description
            "Top-level grouping for the QOS maps associated with the interface";

        container interface-maps {
            description
                "QOS Maps associated with the interface.";

            container config {
                description
                    "Configuration parameters relating to a maps on
                    an interface.";
                uses qos-maps-ext-interface-maps-config;
            }

            container state {
                config false;
                description
                    "Operational state parameters relating to a maps
                    on an interface.";
                uses qos-maps-ext-interface-maps-config;
                uses qos-maps-ext-interface-maps-state;
            }
        }
    }
        
    augment /oc-qos:qos/oc-qos:interfaces/oc-qos:interface {
       description
           "Configuration data for maps associated to interface.";
        uses qos-maps-ext-interface-maps-top;
    }

	augment /oc-qos:qos {
       description
           "Containers for qos maps.";
		uses qos-maps-ext-dscp-maps-top;
		uses qos-maps-ext-dot1p-maps-top;
		uses qos-maps-ext-forwarding-group-queue-maps-top;
		uses qos-maps-ext-forwarding-group-dscp-maps-top;
		uses qos-maps-ext-forwarding-group-dot1p-maps-top;
		uses qos-maps-ext-forwarding-group-priority-group-maps-top;
		uses qos-maps-ext-pfc-priority-queue-maps-top;
		uses qos-maps-ext-pfc-priority-priority-group-maps-top;
	}

    deviation /oc-qos:qos/oc-qos:forwarding-groups/oc-qos:forwarding-group/oc-qos:config/oc-qos:output-queue {
        deviate not-supported;
    }

    deviation /oc-qos:qos/oc-qos:forwarding-groups/oc-qos:forwarding-group/oc-qos:state/oc-qos:output-queue {
        deviate not-supported;
    }

    deviation /oc-qos:qos/oc-qos:forwarding-groups/oc-qos:forwarding-group/oc-qos:config/oc-qos:fabric-priority {
        deviate not-supported;
    }

    deviation /oc-qos:qos/oc-qos:forwarding-groups/oc-qos:forwarding-group/oc-qos:state/oc-qos:fabric-priority {
        deviate not-supported;
    }

    deviation /oc-qos:qos/oc-qos-maps-ext:dscp-maps/oc-qos-maps-ext:dscp-map/oc-qos-maps-ext:dscp-map-entries/oc-qos-maps-ext:dscp-map-entry/config/color {
        deviate not-supported;
    }

    deviation /oc-qos:qos/oc-qos-maps-ext:dscp-maps/oc-qos-maps-ext:dscp-map/oc-qos-maps-ext:dscp-map-entries/oc-qos-maps-ext:dscp-map-entry/state/color {
        deviate not-supported;
    }

    deviation /oc-qos:qos/oc-qos-maps-ext:dot1p-maps/oc-qos-maps-ext:dot1p-map/oc-qos-maps-ext:dot1p-map-entries/oc-qos-maps-ext:dot1p-map-entry/config/color {
        deviate not-supported;
    }

    deviation /oc-qos:qos/oc-qos-maps-ext:dot1p-maps/oc-qos-maps-ext:dot1p-map/oc-qos-maps-ext:dot1p-map-entries/oc-qos-maps-ext:dot1p-map-entry/state/color {
        deviate not-supported;
    }

    deviation
    /oc-qos:qos/oc-qos-maps-ext:forwarding-group-dscp-maps/oc-qos-maps-ext:forwarding-group-dscp-map/oc-qos-maps-ext:forwarding-group-dscp-map-entries/oc-qos-maps-ext:forwarding-group-dscp-map-entry/config/color {
        deviate not-supported;
    }

    deviation
    /oc-qos:qos/oc-qos-maps-ext:forwarding-group-dscp-maps/oc-qos-maps-ext:forwarding-group-dscp-map/oc-qos-maps-ext:forwarding-group-dscp-map-entries/oc-qos-maps-ext:forwarding-group-dscp-map-entry/state/color {
        deviate not-supported;
    }

    deviation
    /oc-qos:qos/oc-qos-maps-ext:forwarding-group-dot1p-maps/oc-qos-maps-ext:forwarding-group-dot1p-map/oc-qos-maps-ext:forwarding-group-dot1p-map-entries/oc-qos-maps-ext:forwarding-group-dot1p-map-entry/config/color {
        deviate not-supported;
    }

    deviation
    /oc-qos:qos/oc-qos-maps-ext:forwarding-group-dot1p-maps/oc-qos-maps-ext:forwarding-group-dot1p-map/oc-qos-maps-ext:forwarding-group-dot1p-map-entries/oc-qos-maps-ext:forwarding-group-dot1p-map-entry/state/color {
        deviate not-supported;
    }
}
