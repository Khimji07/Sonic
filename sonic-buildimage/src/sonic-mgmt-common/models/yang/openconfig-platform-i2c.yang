module openconfig-platform-i2c {
  yang-version 1;

  // namespace

  namespace "http://openconfig.net/yang/platform-i2c/extension";
  prefix oc-pf-i2c;

  import openconfig-extensions { prefix oc-ext; }

  organization
    "Broadcom Inc.";
  contact
    "SONiC";
  description
    "SONIC Platform i2c";
  oc-ext:openconfig-version "0.1.0";

  revision 2022-10-31 {
    description
      "Initial revision.";
    reference
      "0.1.0";
  }


  grouping openconfig-platform-i2c-error-top {
    description
      "Top-level grouping for i2c errors statistics";

        container i2c-errors {
            config false;
            description
                "Top-level container for i2c statistics";
            list i2c-error {
                key "name";
                description "I2C errors counters";

                leaf name {
                    type leafref {
                        path "../state/name";
                    }
                    description
                        "I2C peripheral device name";
                }

                container state {
                    description
                        "I2C errors state";
                    uses i2c-error-stats-config;
                }
            }
         }
   }
   grouping i2c-error-stats-config {
     description "group for i2c-error-stats";
         leaf name {
            type string;
            description
               "I2C peripheral device name";
         }

         leaf dev_addr {
            type string;
            description
               "I2C peripheral device adapter and address in the form of <adapter>-00<i2c-addr-hex>";
         }

         leaf eio {
            type uint64;
            description
               "Number of input/output or transaction failed errors";
         }

         leaf etimedout {
            type uint64;
            description
               "Number of transaction timeout errors";
         }

         leaf ebusy {
            type uint64;
            description
               "Number of SMBus busy errors";
         }

         leaf enxio {
            type uint64;
            description
               "Number of no response or NACK errors";
         }

         leaf einval {
             type uint64;
             description
               "Number of invalid argument errors";
         }

         leaf eagain {
             type uint64;
             description
                "Number of bus arbiteration lost errors";
         }

         leaf eopnotsupp {
             type uint64;
             description
                "Number of unsupported operation errors";
         }

         leaf eproto {
             type uint64;
             description
                "Number of protocol errors";
         }

         leaf timestamp {
             type string;
             description
                "Displays the date/timestamp of i2c-error stats.";
         }
    }

    uses openconfig-platform-i2c-error-top;

    rpc i2c-error-clear {
        description "RPC for clearing the I2C error stats collected so far";

        output {
           leaf status {
              type int32;
              description
                 "The status of the operation execution request.";
           }
           leaf-list status-detail {
              type string;
                 description "The detailed status of the operation execution request.";
           }
       }
    }

}
