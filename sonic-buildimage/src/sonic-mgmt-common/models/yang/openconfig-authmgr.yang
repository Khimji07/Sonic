module openconfig-authmgr {

  yang-version "1";

  // namespace
  namespace "http://openconfig.net/yang/authmgr/extension";

  prefix "oc-authmgr";

  //import openconfig-types { prefix oc-types; }
  //import openconfig-yang-types { prefix oc-yang; }
  import ietf-yang-types {
        prefix yang;
  }
  import openconfig-extensions { prefix oc-ext; }
  import openconfig-interfaces { prefix oc-if; }

  // meta
  organization "OpenConfig working group";

  contact
    "OpenConfig working group
    www.openconfig.net";

  description
    "This module defines configuration and operational state data
    for authentication manager.";

  oc-ext:openconfig-version "0.1.0";

  revision "2021-04-23" {
    description
      "Initial public revision";
    reference "0.1.0";
  }

  // OpenConfig specific extensions for module metadata.
  oc-ext:regexp-posix;
  oc-ext:catalog-organization "openconfig";
  oc-ext:origin "openconfig";

  // identity statements


  // grouping statements

  grouping authmgr-port-config-top {
    description
      "Top-level grouping for interface specific authentication manager feature config";

    list interface {
      key "name";
      description
        "List of interfaces on which PAC is enabled.";

      leaf name {
	type leafref {
          path "../config/name";
        }
        description
          "Reference to the list key";
      }
      container config {
	description
          "Configuration data for PAC on an interface";

        uses authmgr-port-base-config;
      }

      container state {
          config false;
	description
          "PAC State data for the interface";

        uses authmgr-port-base-config;
      }
    }
  }

  grouping authmgr-port-base-config {
    description
        "Grouping for authmgr config parameters";

    leaf name {
        type oc-if:base-interface-ref;
        description
           "Reference to the PAC Ethernet interface";
    }

    leaf port-control-mode {
	type enumeration {
	   enum AUTO {
              description
                 "Enable auto port control mode on a port.";
	   }
	   enum FORCE_AUTHORIZED {
              description
                 "Enable force authorized port control mode on a port.";
	   }
	   enum FORCE_UNAUTHORIZED {
              description
                 "Enable force unauthorized port control mode on a port.";
	   }
	}
	description
	  "Enable 802.1X port control on an interface.
          Note: Enabling PAC on the port will revert all switchport configurations on the port,
          if port control mode is auto/force-unauthorized and port pae role is authenticator.";
    }

    leaf host-control-mode {
	type enumeration {
           enum SINGLE_HOST {
              description
                 "Only single client can communicate through the port.";
           }
           enum MULTI_AUTH {
              description
                 "Enable multi auth mode as host control mode on a port";
           }
           enum MULTI_DOMAIN {
              description
		 "Allows for authentication of multiple clients
            	 individually on one authenticator port.";
           }
           enum MULTI_HOST {
              description
                 "Multiple hosts can communicate over a single port.
                 Only the first supplicant is authenticated while
                 subsequent hosts have network access without having to
                 authenticate";
           }
        }
        description
          "Allow for single or multiple hosts to communicate through
          an 802.1X controlled port.";
    }

    leaf reauth-enable {
        type boolean;
        description
            "Indicates whether Reauthentication is enabled on the port.";
    }

    leaf open-authentication-mode {
        type boolean;
        description
            "Indicates whether Open Authentication mode is enabled on the port.";
    }

    leaf quiet-period {
        type uint32 {
            range 1..65535;
        }
        units "seconds";
        description
            "The initial value of the timer that defines the period
	    during which the Authenticator will not attempt to authenticate the Supplicant.";
    }

    leaf server-timeout {
        type uint32 {
            range 10..65535;
        }
        units "seconds";
        description
            "The timer starts when the access device sends a RADIUS Access-Request packet
             to the Authentication server. The 802.1X authentication fails, if no response
             is received during server timeout period.";
    }

    leaf reauth-period {
        type uint32 {
        range 1..65535;
        }  
        units "seconds";
        description
            "The initial value of the timer that defines the period
            after which the Authenticator will reauthenticate the Supplicant.";
    }

    leaf reauth-period-from-server {
        type boolean;
        description
            "Indicates whether Reauthentication Session timeout from server Enabled or Disabled.";
    }

    leaf max-users-per-port {
        type uint8 {
        range 1..48;
        }
        description
            "Maximum number of clients that can be authenticated
	    on the port. This is applicable only for multi-auth host mode.";
    }

    leaf guest-vlan-id {
        type uint32 {
        range 0..4094;
        }
        description
            "The Guest VLAN Id for the port.";
    }

    leaf auth-fail-vlan-id {
        type uint32 {
        range 0..4094;
        }
        description
            "The Authentication Fail VLAN Id for the port.";
    }
/*
    leaf dead-server-critical-vlan {
    	type uint32 {
       	range 0..4094;
        }
        description
             "Dead server Critical VLAN ID.";
    }

    leaf dead-server-action-voice
    {
      type enumeration {
         enum AUTHORIZE {
            description
                "Allows config of authentication event dead server action voice as authorize.";
         }
         enum NONE {
            description
                "Allows config of authentication event dead server action voice as none.";
         }
      }
      description 
          "Enables configuration of authentication event dead server voice vlan.";
    }

    leaf dead-server-action
    {
      type enumeration {
         enum AUTHORIZE {
            description
                "Allows config of authentication event dead server action as authorize.";
         }
         enum REINITIALIZE {
            description
                "Allows config of authentication event dead server action as reinitialize.";
         }
         enum NONE {
            description
                "Allows config of authentication event dead server action as none.";
         }
      }
      description 
          "Enables configuration of authentication event dead server action.";
    }
*/
    leaf max-reauth-attempts {
       type uint8 {
          range 1..5;
       }
       description
           "The maximum number of authentication retries in the
	   event of authentication failure.";
    }
/*
    leaf server-alive-action
    {
      type enumeration {
         enum REINITIALIZE {
            description
                "Allows config of authentication event server alive action as reinitialize.";
         }
         enum NONE {
            description
               "Allows config of authentication event server alive action as none.";
         }
      }
      description
          "Enables configuration of authentication event server alive action.";
    }
*/
    leaf-list method-list {
      type enumeration {
         enum DOT1X {
	    description
		"Configure authmgr authentication order as DOT1X";
	 }
         enum MAB {
            description
                "Configure authmgr authentication order as MAB";
	 }
      }
      description
          "Enables configuration of authmgr authentication order.";
    }

    leaf-list priority-list {
      type enumeration {
         enum DOT1X {
	    description
		"Configure authmgr authentication priority as DOT1X";
	 }
         enum MAB {
            description
                "Configure authmgr authentication priority as MAB";
	 }
      }
      description 
          "Enables configuration of authmgr authentication priority.";
    }

    leaf port-pae-role {
      type enumeration {
         enum AUTHENTICATOR {
            description
                "Allows config of dot1x port's pae role as authenticator.";
         }
         enum NONE {
            description
                "Allows config of dot1x port's pae role as none.";
         }
      }
      description
          "Enables configuration of dot1x port's pae role.
          Note: Enabling PAC on the port will revert all switchport configurations on the port,
          if port control mode is auto/force-unauthorized and port pae role is authenticator.";
    }
  }

 grouping authmgr-global-base-config {
    description
      "Grouping for authmgr global config parameters";

    leaf monitor-mode-enable {
      type boolean;
      description
        "Enable/disable authentication monitor mode in system";
    }
/*
    leaf max-reauth {
      type uint32 {
        range 1..50;
      }
      description
        "The maximum number of Reauths per second";
    }

    leaf port-control-mode {
        type enumeration {
           enum AUTO {
              description
                 "Enable auto mode as port control mode on a port.";
           }
           enum FORCE_AUTHORIZED {
              description
                 "Enable force authorized mode as port control mode on a port.";
           }
           enum FORCE_UNAUTHORIZED {
              description
                 "Enable force unauthorized mode as port control mode on a port.";
           }
        }
        description
          "Enable 802.1X port control on an interface.";
    }

    leaf host-control-mode {
        type enumeration {
           enum SINGLE_HOST {
              description
                 "Only single client can communicate through the port.";
           }
           enum MULTI_AUTH {
              description
                 "Enable multi auth mode as host control mode on a port";
           }
           enum MULTI_DOMAIN {
              description
                 "Allows for authentication of multiple clients
                 individually on one authenticator port.";
           }
           enum MULTI_HOST {
              description
                 "Multiple hosts can communicate over a single port.
                 Only the first supplicant is authenticated while
                 subsequent hosts have network access without having to
                 authenticate";
           }
        }
        description
          "Allow for single or multiple hosts to communicate through
          an 802.1X controlled port.";
    }

    leaf dynamic-vlan-enable {
      type boolean;
      description
        "Enable/Disable authentication manager dynamic VLAN creation support on the switch.";
    }

    leaf vlan-assign-enable {
      type boolean;
      description
        "Enable/Disable RADIUS VLAN assignment support on the switch.";
    }
*/
 }

  grouping authmgr-global-config-top {
     description
        "Top-level Grouping for authentication manager global config";

     container config {
        description
          "Config conatiner for authentication manager global configuration";

        uses authmgr-global-base-config;
     }

    container state {
       config false;

       description
         "State container for authentication manager global state data";

       uses authmgr-global-base-config;
    }
  }

  grouping authmgr-authenticated-clients-state {
      description
        "Grouping for 802.1X sessions State data.";

            	leaf name {
      		     type oc-if:base-interface-ref;
      		     description
        		"Reference to the PAC Ethernet interface";
    	    	}

                leaf macaddress {
                    type yang:mac-address;
                    description
                        "MAC address of authenticated client.";
                }

                leaf auth-status {
		    type enumeration {
                       enum AUTHORIZED {
			  description
                 	      "Client Auth status - authorized.";
		       }
                       enum UNAUTHORIZED {
			  description
                 	      "Client Auth status - unauthorized.";
		       }
                    }
                    description
                        "Authentication status of the client.";
                }

                leaf authenticated-method {
		    type enumeration {
                       enum "802.1X" {
                          description
                              "Client authenticated method - 802.1X.";
                       }
                       enum MAB {
                          description
                              "Client authenticated method - MAB.";
                       }
                       enum NONE {
                          description
                              "Client authenticated method - NONE.";
                       }
                    }
                    description
                        "Client authenicated method - 802.1x or mab or none.";
                }

                leaf session-timeout-RADIUS {
                    type uint32;
                    description
                        "Session timeout value received from RADIUS server.";
                }

                leaf session-timeout-oper {
                    type uint32;
                    description
                        "Operational value of the Client session timeout.";
                }

		leaf user-name {
                    type string {
                        length 1..31;
                    }
		    description
                        "Client user name.";
                }

                leaf termination-action {
                    type uint8 {
                        range "0..1" {
                           error-message " termination action valid range are 0-1.";
                        }
                    }
                    description
                         "Client action on session timeout.";
                }

                leaf vlan-id {
                    type uint32 {
                        range 1..4094;
                    }
                    description
                         "VLAN associated with the authorized client.";
                }
	
		leaf vlan-type {
                    type enumeration {
                         enum RADIUS {
			    description
				"Authenticated client vlan type - RADIUS.";
			 }
                         enum DEFAULT {
			    description
				"Authenticated client vlan type - Default.";
			 }
                         enum VOICE {
			    description
				"Authenticated client vlan type - Voice.";
			 }
                         enum CRITICAL {
			    description
				"Authenticated client vlan type - Critical.";
			 }
                         enum UNAUTHENTICATED {
			    description
				"Authenticated client vlan type - Unauthenticated.";
			 }
                         enum GUEST {
			    description
				"Authenticated client vlan type - Guest.";
			 }
                         enum MONITOR {
			    description
				"Authenticated client vlan type - Monitor.";
                    	 }
		    }
                    description
                        "Authorization status of the client.";
                }

                leaf backend-auth-method {
		    type enumeration {
                         enum RADIUS {
                    	    description
                                "Radius server backend authentication method used to authorize the client.";
			 }
                         enum UNDEFINED {
                            description
                                "No valid backend authentication method.";
                         }
                    }
                    description
                        "Backend authentication method used to authorize the client.";
                }

                leaf session-time {
                    type uint32;
                    description
                         "Client session time.";
                }

                leaf termination-action-time-left {
                    type int32;
                    description
                         "Time left for authenticated client termination action.";
                }

		leaf dacl-name {
                    type string {
                        length "0..512" {
                           error-message "valid length for dacl name is 0-512.";
                           error-app-tag dacl-name-invalid;
                        }
                    }
                    description
                        "Dynamic ACL name.";
                }

                leaf redirect-acl-name {
                    type string {
                        length "0..256" {
                           error-message "valid length for redirect ACL name is 0-256.";
                           error-app-tag redirect-acl-name-invalid;
                        }
                    }
                    description
                        "The Redirect ACL is a static ACL sent in the RADIUS attribute redirect-acl.
                         It is used to redirect matching packets to the CPU for further action.";
                }

                leaf redirect-url {
                    type string {
                        length "0..256" {
                           error-message "valid length for redirect URL is 0-256.";
                           error-app-tag redirect-url-invalid;
                        }
                    }
                    description
                        "The Redirect URL is a URL sent in the RADIUS attribute redirect-url.
                         It is used by the Redirect component logic to redirect matching packets the redirect URL by using HTTP 302 response code.";
                }
  }

  grouping authmgr-authenticated-clients-history-state {
      description
        "Grouping for authmgr authenticated clients history state data.";

            	leaf name {
                    type oc-if:base-interface-ref;
                    description
                	"Reference to the PAC Ethernet interface";
            	}

                leaf index {
                    type uint8 {
                        range 1..20;
                    }
                    description
                        "authentication clients history - index.";
                }

		leaf timestamp {
		    type string;
                        description
                          "Displays the date/timestamp of authmgr client being authenticated.";
                }

                leaf client-mac-addr {
                    type yang:mac-address;
                    description
                        "MAC address of authenticated client.";
                }

		leaf authenticated-method {
                    type enumeration {
                       enum "802.1X" {
                          description
                              "Client authenticated method - 802.1X.";
                       }
                       enum MAB {
                          description
                              "Client authenticated method - MAB.";
                       }
                       enum NONE {
                          description
                              "Client authenticated method - NONE.";
                       }
                    }
                    description
                        "Client authenicated method - 802.1x or mab or none.";
                }

		leaf auth-status {
                    type enumeration {
                       enum AUTHORIZED {
                          description
                              "Client Auth status - authorized.";
                       }
                       enum UNAUTHORIZED {
                          description
                              "Client Auth status - unauthorized.";
                       }
                    }
                    description
                        "Authentication status of the client.";
                }

  }

  grouping authmgr-port-operational-state {
      description
        "Grouping for pac port operational state data.";

                leaf name {
                    type oc-if:base-interface-ref;
                    description
                        "Reference to the PAC Ethernet interface";
                }

		leaf-list enabled-method-list {
                   type enumeration {
                        enum DOT1X {
			   description
			       "DOT1X authentication type enabled for authmgr authentication.";
			}
                        enum MAB {
                           description
			       "MAB authentication type enabled for authmgr authentication.";
                        }
			enum UNDEFINED {
                           description
                               "authentication method not available.";
                        }
                   }
                   description
                        "Relative method order to be used for authmgr authentication.";
                }

                leaf-list enabled-priority-list {
                   type enumeration {
                        enum DOT1X {
			   description
			       "DOT1X authentication type enabled as priority for authmgr authentication.";
			}
                        enum MAB {
                           description
			       "MAB authentication type enabled as prirority for authmgr authentication.";
                        }
			enum UNDEFINED {
                           description
                               "authentication method not available.";
                        }
                   }
                   description
                        "Relative priority of methods to be used for authmgr authentication.";
                }
  }

  grouping authmgr-global-oper-state {
      description
        "Grouping for authmgr global operational state db data.";

               leaf num-clients-authenticated {
                   type uint16;
                   description
                        "Number of clients authenticated.";
                }

                leaf num-clients-authenticated-monitor {
                   type uint16;
                   description
                        "Number of clients authenticated in Monitor mode.";
                }
  }

  grouping authmgr-authenticated-sessions-top {
      description
        "Top-level grouping for authentication manager 802.1X sessions.";

      container authmgr-authenticated-clients {
        config false;
        description
          "Top level container for authenticated sessions state data.";

        list authenticated-client {
          key "name macaddress";
          config false;
          description
            "The list of authenticated clients on a interface.";

          leaf name {
            type leafref {
              path "../state/name";
            }
            description
              "Client interface.";
          }

	  leaf macaddress {
            type leafref {
              path "../state/macaddress";
            }
            description
               "Reference to connected client MAC addr.";
     	  }

          container state {
            config false;
            description
              "Top level state container for authentication manager 802.1X sessions.";

            uses authmgr-authenticated-clients-state;
          }
        }
      }

     container authmgr-authenticated-clients-history {
        description
          "Top level container for authenticated clients history state data.";

        list entry {
          key "name index";
          config false;
          description
            "The list of authenticated clients history on a interface.";

          leaf name {
            type leafref {
              path "../state/name";
            }
            description
              "Client interface.";
          }

	  leaf index {
            type leafref {
              path "../state/index";
            }
            description
              "authentication clients history - index.";
          }

          container state {
            config false;
            description
              "Top level state container for 802.1X authenticated clients history state data.";

            uses authmgr-authenticated-clients-history-state;
          }
        }
     }

     container authmgr-port-operational-state-data {
        description
          "Top level container for pac port operational state data.";

        list ifname {
          key "name";
          config false;
          description
            "Reference to port operational physical interface.";

          leaf name {
            type leafref {
              path "../state/name";
            }
            description
              "Port physical interface name.";
          }

          container state {
            config false;
            description
              "Top level state container for pac port operational state data.";

            uses authmgr-port-operational-state;
          }
        }
     }

     container authmgr-global-operational-state-data {
	config false;
        description
          "Container for authentication manager global operational state db data.";

        container state {
          config false;

          description
            "State container for authentication manager global operational state db data";

          uses authmgr-global-oper-state;
        }
     }
  }

  grouping authmgr-top {
    description
        "Top-level grouping for authentication manager.";

    container authmgr {
        description
            "Top-level container for authentication manager configuration and
            state data";

    container authmgr-global-config {
	description 
            "Container for authentication manager global configuration
	    and operation data";

        uses authmgr-global-config-top;
    }

    container authmgr-port-config {
        description
            "Enclosing container for authentication manager per port configuration 
	    and state data";

        uses authmgr-port-config-top;
    }

    uses authmgr-authenticated-sessions-top;

    }
  }

  // data definition statements

  uses authmgr-top;
}
