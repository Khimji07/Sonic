module openconfig-chassis-locator-led {

    yang-version "1";

    namespace "http://openconfig.net/yang/system/chassis-locator-led/extension";

    prefix "oc-loc-led";

    import openconfig-extensions { prefix oc-ext; }


    organization
        "Broadcom Inc.";
    contact
        "SONiC";
    description
        "SONIC Chassis Locator LED";

    revision 2021-09-16 {
        description
            "Initial revision.";
        reference
            "0.1.0";
    }

    oc-ext:openconfig-version "0.1.0";


        rpc locator-led-chassis-on {
            description
                "Enable Locator Chassis LED";
            input {
                leaf timer{
                    type uint16{
                        range "1..120" {
                             error-message "out of range: timer value in minutes 1-120";
                        }
                    }
                description
                    "timer value in minutes: 1-120";
                }
             }

            output {
                leaf-list status-detail{
                    type string;
                    description
                         "The detailed status of the operation execution request.";
                }
            }
         }

         rpc locator-led-chassis-off {
             description
                   "Disable Locator Chassis LED";
             output {
                leaf status{
                     type string;
                     description
                         "The detailed status of the operation execution request.";
                }
             }
         }

         rpc show-locator-led-chassis {
             description
                  "Show Locator Chassis LED State";
             output {
                  leaf-list status-detail{
                  type string;
                  description
                       "The detailed status of the operation execution request.";
                  }
             }
         }

}
