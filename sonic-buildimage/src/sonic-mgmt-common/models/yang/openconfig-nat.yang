module openconfig-nat {

    yang-version "1";

    // namespace
    namespace "http://openconfig.net/yang/nat/extension";

    prefix "oc-nat";

    // import some basic types
    import openconfig-inet-types { prefix oc-inet; }
    import openconfig-yang-types { prefix oc-yang; }
    import openconfig-extensions { prefix oc-ext; }

    // meta
    organization "OpenConfig working group";

    contact
        "OpenConfig working group
        netopenconfig@googlegroups.com";

    description
        " ";

    oc-ext:openconfig-version "0.1.0";

    revision "2019-11-15" {
        description
            "Initial draft version";
        reference "0.1.0";
    }

    // OpenConfig specific extensions for module metadata.
    oc-ext:regexp-posix;
    oc-ext:catalog-organization "openconfig";
    oc-ext:origin "openconfig";

    // extension statements

    // feature statements

    // identity statements


    identity NAT_TYPE {
        description
            "Base identity for types of NAT/NAPT mappings.";
    }

    identity SNAT {
        base NAT_TYPE;
        description
            "Source NAT type.";
    }

    identity DNAT {
        base NAT_TYPE;
        description
            "Desination NAT type.";
    }

    identity NAT_ENTRY_TYPE {
        description
            "Base identity for for types of STATIC/DYNAMIC mappings.";
    }

    identity STATIC {
        base NAT_ENTRY_TYPE;
        description
            "Static entry type.";
    }

    identity DYNAMIC {
        base NAT_ENTRY_TYPE;
        description
            "Dynamic entry type.";
    }

    typedef ip-addr-type {
        type union {
          type oc-inet:ipv4-address;
          type string {
                          pattern '(25[0-5]|2[0-4][0-9]|1[0-9][0-9]|[1-9]?[0-9])\.(25[0-5]|2[0-4][0-9]|1[0-9][0-9]|[1-9]?[0-9])\.(25[0-5]|2[0-4][0-9]|1[0-9][0-9]|[1-9]?[0-9])\.(25[0-5]|2[0-4][0-9]|1[0-9][0-9]|[1-9]?[0-9])(-(25[0-5]|2[0-4][0-9]|1[0-9][0-9]|[1-9]?[0-9])\.(25[0-5]|2[0-4][0-9]|1[0-9][0-9]|[1-9]?[0-9])\.(25[0-5]|2[0-4][0-9]|1[0-9][0-9]|[1-9]?[0-9])\.(25[0-5]|2[0-4][0-9]|1[0-9][0-9]|[1-9]?[0-9]))?';
                      }
        }

        description
          "This type denotes a single IPv4 address or a range of IPv4 addresses.";
    }

    grouping nat-napt-mapping-table-config {
        description
            "NAPT mapping config table.";

        leaf external-address {
            type oc-inet:ip-address;
            description
                "External interface of the NAPT.";
        }

        leaf external-port {
            type oc-inet:port-number;
            description
                "External port of the packet sent/receive on an external
                interface of the NAPT.";
        }

        leaf protocol {
            type uint8;
            description
                "The protocol associated with this mapping values.";
        }

        leaf internal-address {
            type oc-inet:ip-address;
            mandatory true;
            description
                "Internal interface of the NAPT.";
        }

        leaf internal-port {
            type oc-inet:port-number;
            mandatory true;
            description
                "Internal port of the packet sent/receive on an internal
                interface of the NAPT.";
        }

        leaf type {
            type identityref {
                base NAT_TYPE;
            }
            default DNAT;
            description
                "Type of the NAT to be done, Source NAPT (SNAT) or
                Destination NAPT(DNAT).";
        }

        leaf twice-nat-id {
            type uint16 {
                range "1..9999";
            }

            description
                "Group ID used for twice NAPT.";
        }
    }

    grouping nat-napt-mapping-table-state {
        description
            "NAPT mapping state table.";

        leaf translated-ip {
            type oc-inet:ip-address;
            description
                "Translated interface associated with this NAPT entry.";
        }

        leaf translated-port {
            type oc-inet:port-number;
            description
                "Translated port associated with this NAPT entry.";
        }

        leaf entry-type {
            type identityref {
                base NAT_ENTRY_TYPE;
            }
            description
                "NAPT Entry type (STATIC/DYNAMIC).";
        }

        container counters {
            description
                "Counters associated with this NAPT entry.";

            uses nat-type-counters-common-top;
        }
    }

    grouping nat-napt-mapping-top {
        description
            "Top grouping for NAPT config, state and counters data.";

        container napt-mapping-table {
            description
                "NAPT mapping table.";

            list napt-mapping-entry {
                key "external-address protocol external-port";
                description
                    "NAPT mapping entry list.";

                leaf external-address {
                    type leafref {
                        path "../config/external-address";
                    }
                    description
                        "External interface of the NAPT.";
                }

                leaf external-port {
                    type leafref {
                        path "../config/external-port";
                    }
                    description
                        "External port of the packet sent/receive on an external
                        interface of the NAPT.";
                }

                leaf protocol {
                    type leafref {
                        path "../config/protocol";
                    }
                    description
                        "The protocol associated with this mapping values.";
                }

                container config {
                    description
                        "NAPT config data.";

                    uses nat-napt-mapping-table-config;
                }

                container state {
                    config false;
                    description
                        "NAPT state data.";

                    uses nat-napt-mapping-table-config;
                    uses nat-napt-mapping-table-state;
                }
            }
        }
    }

    grouping nat-mapping-table-config {
        description
            "NAT mapping config table.";

        leaf external-address {
            type oc-inet:ip-address;
            description
                "External interface of the NAT.";
        }

        leaf internal-address {
            type oc-inet:ip-address;
            description
                "Internal interface of the NAT.";
        }

        leaf type {
            type identityref {
                base NAT_TYPE;
            }
            default DNAT;
            description
                "Type of the NAT to be done, Source NAPT (SNAT) or
                Destination NAPT(DNAT).";
        }

        leaf twice-nat-id {
            type uint16 {
                range "1..9999";
            }
            description
                "Group ID used for twice NAT.";
        }
    }

    grouping nat-mapping-table-state {
        description
            "NAT mapping state table.";

        leaf translated-ip {
            type oc-inet:ip-address;
            description
                "Translated interface associated with this NAT entry.";
        }

        leaf entry-type {
            type identityref {
                base NAT_ENTRY_TYPE;
            }
            description
                "NAPT Entry type (STATIC/DYNAMIC).";
        }

        container counters {
            description
                "Counters associated with this NAT entry.";
            uses nat-type-counters-common-top;
        }
    }

    grouping nat-mapping-top {
        description
            "Top grouping for NAT config, state and counters data.";

        container nat-mapping-table {
            description
                "NAT mapping table.";
            list nat-mapping-entry {
                key "external-address";
                description
                    "NAT mapping entry list.";

                leaf external-address {
                    type leafref {
                        path "../config/external-address";
                    }
                    description
                        "External interface of the NAT.";
                }

                container config {
                    description
                        "NAT config data.";

                    uses nat-mapping-table-config;
                }

                container state {
                    config false;
                    description
                        "NAT state data.";

                    uses nat-mapping-table-config;
                    uses nat-mapping-table-state;
                }
            }
        }
    }

    grouping nat-twice-mapping-table-config {
        description
            "Top grouping for twice NAT mapping config table.";

        leaf src-ip {
            type oc-inet:ip-address;
            description
                "The source interface associated with this NAT entry.";
        }

        leaf dst-ip {
            type oc-inet:ip-address;
            description
                "The destination interface associated with this NAT entry.";
        }
    }

    grouping nat-twice-mapping-table-state {
        description
            "Top grouping for twice NAT mapping state table.";

        leaf translated-src-ip {
            type oc-inet:ip-address;
            description
                "Translated source interface associated with this NAT entry.";
        }

        leaf translated-dst-ip {
            type oc-inet:ip-address;
            description
                "Translated destination interface associated with this NAT entry.";
        }

        leaf entry-type {
            type identityref {
                base NAT_ENTRY_TYPE;
            }
            description
                "NAT Entry type (STATIC/DYNAMIC).";
        }

        container counters {
            description
                "Counters associated with this NAT entry.";
            uses nat-type-counters-common-top;
        }
    }

    grouping nat-napt-twice-mapping-table-config {
        description
            "Top grouping for twice NAPT mapping state table.";

        leaf protocol {
            type uint8;
            description
                "The protocol associated with this NAPT entry.";
        }

        leaf src-ip {
            type oc-inet:ip-address;
            description
                "The source interface associated with this NAPT entry.";
        }

        leaf src-port {
            type oc-inet:port-number;
            description
                "The Source port associated with this NAPT entry.";
        }

        leaf dst-ip {
            type oc-inet:ip-address;
            description
                "The destination interface associated with this NAPT entry.";
        }

        leaf dst-port {
            type oc-inet:port-number;
            description
                "The destination port associated with this NAPT entry.";
        }
    }

    grouping nat-napt-twice-mapping-table-state {
        description
            "Top grouping for twice NAPT mapping state table.";


        leaf translated-src-ip {
            type oc-inet:ip-address;
            description
                "Translated source interface associated with this NAPT entry.";
        }

        leaf translated-src-port {
            type oc-inet:port-number;
            description
                "Translated source port associated with this NAPT entry.";
        }

        leaf translated-dst-ip {
            type oc-inet:ip-address;
            description
                "Translated destination interface associated with this NAPT entry.";
        }

        leaf translated-dst-port {
            type oc-inet:port-number;
            description
                "Translated destination port associated with this NAPT entry.";
        }

        leaf entry-type {
            type identityref {
                base NAT_ENTRY_TYPE;
            }
            description
                "NAT Entry type (STATIC/DYNAMIC).";
        }

        container counters {
            description
                "Counters associated with this NAPT entry.";
            uses nat-type-counters-common-top;
        }
    }

    grouping nat-twice-mapping-top {
        description
            "Top grouping for twice NAT mapping.";

        container nat-twice-mapping-table {
            description
                "Twice NAT mapping table.";

            list nat-twice-entry  {
                key "src-ip dst-ip";

                description
                    "Twice NAT mapping state entry list.";

                leaf src-ip {
                    type leafref {
                        path "../config/src-ip";
                    }
                    description
                        "The source interface associated with this NAT entry.";
                }

                leaf dst-ip {
                    type leafref {
                        path "../config/dst-ip";
                    }
                    description
                        "The destination interface associated with this NAT entry.";
                }

                container config {
                    description
                        "Twice NAT config data.";
                    uses nat-twice-mapping-table-config;
                }

                container state {
                    config false;
                    description
                        "Twice NAT state data.";

                    uses nat-twice-mapping-table-config;
                    uses nat-twice-mapping-table-state;
                }
            }
        }
    }

    grouping nat-napt-twice-mapping-top {
        description
            "Top grouping for twice NAPT mapping.";

        container napt-twice-mapping-table {
            description
                "Twice NAPT mapping table.";

            list napt-twice-entry {
                key "protocol src-ip src-port dst-ip dst-port";
                description
                    "Twice NAPT mapping state entry list.";

                leaf protocol {
                    type leafref {
                        path "../config/protocol";
                    }
                    description
                        "The protocol associated with this NAPT entry.";
                }

                leaf src-ip {
                    type leafref {
                        path "../config/src-ip";
                    }
                    description
                        "The source interface associated with this NAPT entry.";
                }

                leaf src-port {
                    type leafref {
                        path "../config/src-port";
                    }
                    description
                        "The Source port associated with this NAPT entry.";
                }

                leaf dst-ip {
                    type leafref {
                        path "../config/dst-ip";
                    }
                    description
                        "The destination interface associated with this NAPT entry.";
                }

                leaf dst-port {
                    type leafref {
                        path "../config/dst-port";
                    }
                    description
                        "The destination port associated with this NAPT entry.";
                }

                container config {
                    description
                        "Twice NAPT config data.";
                    uses nat-napt-twice-mapping-table-config;
                }

                container state {
                    config false;
                    description
                        "Twice NAPT state data.";
                    uses nat-napt-twice-mapping-table-config;
                    uses nat-napt-twice-mapping-table-state;
                }
            }
        }
    }

    grouping nat-type-counters-common-top {
        description
            "Top grouping for NAT counters.";

        leaf nat-translations-pkts {
            type oc-yang:counter64;
            description
                "NAT translations packet count.";
        }

        leaf nat-translations-bytes {
            type oc-yang:counter64;
            description
                "NAT translations byte count.";
        }
    }

    grouping nat-pool-config {
        description
            "Top grouping for NAT pool data.";

        leaf pool-name {
            type string;
            description
                "NAT pool name.";
        }

        leaf nat-ip {
            type ip-addr-type;
            mandatory true;
            description
                "NAT Pool can be configured using either a single IP or an IP address range.";
        }

        leaf nat-port {
            type string {
                pattern "[0-9]{1,5}(-)[0-9]{1,5}";
                oc-ext:posix-pattern '^[0-9]{1,5}(-)[0-9]{1,5}$';
            }
            description
                "NAT port range.";
        }
    }

    grouping nat-pool-top {
        description
            "Top grouping for NAT pool config and state data.";

        container nat-pool {
            description
                "NAT pool mapping table.";

            list nat-pool-entry {
                key "pool-name";
                description
                    "NAT pool mapping entry.";


                leaf pool-name {
                    type leafref {
                        path "../config/pool-name";
                    }
                    description
                        "NAT pool name.";
                }

                container config {
                    description
                        "NAT pool config data.";

                    uses nat-pool-config;
                }
                container state {
                    config false;
                    description
                        "NAT pool state data.";

                    uses nat-pool-config;
                }
            }
        }

    }

    grouping nat-acl-pool-binding-config {
        description
            "Top grouping for NAT ACL pool binding entry data.";

        leaf name {
            type string;
            description
                "NAT ACL pool binding name.";
        }

        leaf access-list {
            type string;
            description
                "Access list name.";
        }

        leaf nat-pool {
            type string;
            mandatory true;
            description
                "NAT pool name.";
        }

        leaf type {
            type identityref {
                base NAT_TYPE;
            }
            description
                "Type of the NAT to be done, Source NAPT (SNAT) or
                Destination NAPT(DNAT).";
        }

        leaf twice-nat-id {
            type uint16 {
               range "1..9999";
            }
            description
                "Group ID used for twice NAPT.";
        }

    }

    grouping nat-acl-pool-binding-top {
        description
            "Top grouping for NAT ACL to pool binding.";

        container nat-acl-pool-binding {
            description
                "NAT ACL to pool binding table.";

            list nat-acl-pool-binding-entry {
                key "name";
                description
                    "NAT ACL to pool binding entry.";

                leaf name {
                    type leafref {
                        path "../config/name";
                    }
                    description
                        "NAT ACL pool binding name.";
                }

                container config {
                    description
                        "NAT ACL to pool binding config data.";

                    uses nat-acl-pool-binding-config;
                }
                container state {
                    config false;
                    description
                        "NAT ACL to pool binding state data.";

                    uses nat-acl-pool-binding-config;
                }
            }
        }
    }

    grouping nat-zone-top {
        description
            "Top grouping for NAT zone config, state and counters data.";
        container nat-zone {
            description
                "NAT zone counters data.";
            list nat-zone-entry {
                key "zone-id";
                description
                    "NAT zone entry.";

                leaf zone-id {
                    type leafref {
                        path "../config/zone-id";
                    }
                    description
                        "NAT zone id.";
                }
                container config {
                    description
                        "NAT Zone config container.";
                    uses nat-zone-config;
                }

                container state {
                    config false;
                    description
                        "NAT Zone state container.";
                    uses nat-zone-config;
                    uses nat-zone-state;
                }

            }
        }
    }

    grouping nat-zone-config {
        description
            "Grouping for NAT Zone configuration.";
        leaf zone-id {
            type uint8;
            description
                "NAT zone id.";
        }
    }

    grouping nat-zone-state {
        description
            "Grouping for NAT Zone state data.";
        container counters {
            config false;
            description
                "NAT zone counters table.";

            uses nat-zone-counters-top;
        }
    }

    grouping nat-zone-counters-top {
        description
            "Top grouping for NAT zone counters data.";


        leaf dnat-discards {
            type oc-yang:counter64;
            description
                "DNAT discards counter.";
        }

        leaf snat-discards {
            type oc-yang:counter64;
            description
                "SNAT discards counter.";
        }

        leaf dnat-translation-needed {
            type oc-yang:counter64;
            description
                "DNAT translation needed counter.";
        }

        leaf snat-translation-needed {
            type oc-yang:counter64;
            description
                "SNAT translation needed counter.";
        }

        leaf dnat-translations {
            type oc-yang:counter64;
            description
                "DNAT translations counter.";
        }

        leaf snat-translations {
            type oc-yang:counter64;
            description
                "SNAT translations counter.";
        }
    }

    grouping nat-instance-config {
        description
            "NAT instance configuration.";

        leaf id {
            type uint32;
            must '. >= 1';
            description
                "NAT instance identifier.
                The identifier must be greater than zero.";
        }


        leaf enable {
            type boolean;
            default true;
            description
                "Status of the NAT instance.";
        }

        leaf timeout {
            type uint32 {
                range "300..432000";
            }
            units "seconds";
            description
                "NAT global timeout.";
        }

        leaf tcp-timeout {
            type uint32 {
                range "300..432000";
            }
            units "seconds";
            description
                "NAT TCP timeout.";
        }

        leaf udp-timeout {
            type uint32 {
                range "120..600";
            }
            units "seconds";
            description
                "NAT UDP timeout.";
        }

    }

    grouping nat-instance-top {
        description
            "NAT instance configuration.";

        container instances {
            description
                "NAT instances";

            list instance {
                key "id";
                description
                    "A NAT instance.  This identifier can be automatically
                    assigned or explicitly configured.";

                leaf id {
                    type leafref {
                        path "../config/id";
                    }
                    description
                        "NAT instance identifier.
                        The identifier must be greater than zero.";
                }
                container config {
                    description
                        "NAT global config data.";
                    uses nat-instance-config;
                }

                container state {
                    config false;
                    description
                        "NAT global state data.";
                    uses nat-instance-config;
                }

                uses nat-napt-mapping-top;
                uses nat-mapping-top;
                uses nat-pool-top;
                uses nat-acl-pool-binding-top;
                uses nat-zone-top;
                uses nat-twice-mapping-top;
                uses nat-napt-twice-mapping-top;
            }
        }
    }


    grouping nat-top {
        description
            "Top level nat data containers";

        container nat {
            description
                "Enclosing container for nat-related configuration and
                operational state data";

            uses nat-instance-top;
        }

    }

    // data definition statements

    uses nat-top;
}
