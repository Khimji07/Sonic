module openconfig-show-techsupport-private {

    yang-version "1";

    // namespace
    namespace "http://openconfig.net/yang/show-techsupport-private/extension";

    prefix "oc-show-techsupport-private";

    import ietf-yang-types {
         prefix yang;
    }

    import openconfig-extensions { prefix oc-ext; }

    organization "Dell";

    contact
      "Dell";

    description
      "This module describes private definition for technical support information model.";

    oc-ext:openconfig-version "0.1.0";

    revision "2021-08-28" {
      description
        "Initial version.";
      reference "0.1.0";
    }

    // rpc statements
    rpc show-techsupport-info {
        description
          "RPC to initiate collection of technical support information.";
        input {
            leaf date {
                type yang:date-and-time;
                description
                    "Date and time specification of the desired start
                    point for collected log and core information";
            }
        }
        output {
            leaf status {
                type uint32;
                description
                  "The status of the operation execution request. 0 for SUCCESS and 1 for ERROR.";
            }
            leaf status-detail {
                type string;
                description
                    "Detailed status of the operation execution request.";
            }
            leaf output-filename {
                type string;
                description
                    "Name of the host compressed tar file containing the collected
                    technical support information";
            }
        }
    }

    rpc show-techsupport-cancel {
        description
          "RPC to cancel active collection of technical support information.";
        output {
            leaf status {
                type uint32;
                description
                  "The status of the cancelation execution request. 0 for SUCCESS and 1 for ERROR.";
            }
            leaf status-detail {
                type string;
                description
                    "Detailed status of the cancelation execution request.";
            }
        }
    }

}
