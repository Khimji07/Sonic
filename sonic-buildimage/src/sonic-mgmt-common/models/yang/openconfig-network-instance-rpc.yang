module openconfig-network-instance-rpc {

    yang-version "1";

    // namespace
    namespace "http://openconfig.net/yang/network-instance-rpc/extension";

    prefix "oc-netinst-rpc";

    // meta
    organization 
        "SONiC";

    contact 
        "SONiC";

    description
        "This module defines rpc configuration
        for the network-instance.";

    revision "2024-03-06" {
        description
            "Initial public revision";
        reference "0.1.0";
    }

    //rpcs
    rpc clear-fdb {
        description 
            "RPC for clearing fdb mac address-table.";

        input {
            leaf mac-param {
                type string;
                description
                    "parameter for deleting either all dynamic mac address or a record related to interface name / vlan id";
            }
        }
        output {
            leaf status {
                type string;
                    description
                        " success / failure of deletion of dynamic mac address";
            }
        }
    }
}
