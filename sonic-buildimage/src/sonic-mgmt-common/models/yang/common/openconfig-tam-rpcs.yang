submodule openconfig-tam-rpcs {
    yang-version 1.1;

    // main module reference
    belongs-to openconfig-tam {
        prefix oc-tam;
    }

    // import some basic types
    import openconfig-extensions {
        prefix oc-ext;
    }

    // meta
    organization
        "SONiC";

    contact
        "SONiC";

    description
        "Silicon Telemetry Module";

    revision 2020-06-01 {
        description
            "Defintion of all TAM feature related RPCs";
        reference
            "3.2.0";
    }

    // extension statements
    oc-ext:openconfig-version "3.2.0";

    // rpc statements
    rpc clear-flowgroup-counters {
        description
            "Clear the counters of the flowgroup";
        input {
            leaf name {
                type string;
                description
                    "Name of the flowgroup for which the counters need to be cleared;
                when not supplied, all the Flowgroup counters are cleared";
            }
        }
        output {
            leaf status {
                type int32;
                description
                    "The status of the operation execution request.";
            }
            leaf-list status-detail {
                type string;
                description "The detailed status of the operation execution request.";
            }
        }
    }
}
