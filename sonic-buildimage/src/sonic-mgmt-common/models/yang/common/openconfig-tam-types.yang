module openconfig-tam-types {
    yang-version 1.1;

    // namespace
    namespace "http://openconfig.net/yang/tam/types/extension";

    prefix oc-tam-types;

    // import some basic types
    import openconfig-extensions {
        prefix oc-ext;
    }

    // include submodules
    // meta
    organization
      "SONiC";

    contact
      "SONiC";

    description
      "Silicon Telemetry Module";

    revision 2020-06-01 {
        description
          "Initial revision";
        reference
          "3.2.0";
    }

    // extension statements
    oc-ext:openconfig-version "3.2.0";

    // feature statements
    // identity statements
    identity TAM_FEATURE {
        description
          "TAM feature identification";
    }

    // typedef statements
    typedef tam-feature-stautus-type {

        type enumeration {
            enum ACTIVE {
                description
                  "Feature is active";
            }
            enum INACTIVE {
                description
                  "Feature is suspended/inactive";
            }
            enum UNSUPPORTED {
                description
                  "Feature is unsupported on the switch";
            }
            enum INSUFFICIENT_RESOURCES {
                description
                  "Feature requires resources before
                   it can be made active";
            }
        }

        description
          "Status of a given TAM feature";
    }

    typedef tam-name-type {
        type string {
            length "1..32";
            pattern '[a-zA-Z0-9]{1}([-a-zA-Z0-9_]{0,32})';
            oc-ext:posix-pattern "^[a-zA-Z0-9]{1}([-a-zA-Z0-9_]{0,32})$";
        }
        description
            "Type definition for name string used across TAM feature";
    }

// grouping statements
// data definition statements
// augment statements
// rpc statements
// notification statements
}
