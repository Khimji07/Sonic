module openconfig-port-breakout-ext {

    yang-version "1";

    // namespace
    namespace "http://openconfig.net/yang/platform/port/extension";

    prefix "oc-pf-ext";

    import openconfig-extensions { prefix "oc-ext"; }
    import openconfig-platform { prefix oc-pf; }
    import openconfig-platform-port { prefix oc-port; }

    organization "SONiC";
    contact
        "SONiC";
    description
        "This module contains a collection of YANG extension for
           breakout port";

    oc-ext:openconfig-version "0.12.3";

    revision 2021-12-07 {
        description
            "Adapted to the latest changes to openconfig-platform-port.yang.";
        reference "0.12.3";
    }

    revision 2020-06-10 {
        description
            "Initial revision.";
        reference "0.12.2";
    }

    grouping group-state-top {
      description
        "Operational state data for the port breakout group.";
        leaf status {
            type string;
            description "Status of breakout operation";
        }

        leaf-list members {
            type string;
            description "List of brokenout member ports";
        }
    }
    augment /oc-pf:components/oc-pf:component/oc-pf:port/oc-port:breakout-mode/oc-port:groups/oc-port:group/oc-port:state {
        description "Additional fields for port breakout state";
        uses group-state-top;
    }
}
