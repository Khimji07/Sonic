module openconfig-dhcp-snooping-rpc {

  yang-version "1.1";

  //namespace
  namespace "http://openconfig.net/yang/dhcp-snooping-rpc/extension";
  prefix "oc-dhcp-snooping-rpc";

  //meta
  organization
    "SONiC";

  contact
    "SONiC";

  description
    "This module defines configuration and operational state data for DHCP Snooping";

  revision "2021-07-22" {
    description
      "Initial draft.";
    reference "1.0.2";
  }

  rpc clear-dhcp-snooping-binding {

    description "RPC for clearing DHCP snooping binding entries. Input can be :
        1. V4_ONE as clear-type for clearing specific binding entry with MAC, interface, VLAN and IP address.
        2. V4_ALL as clear-type for clearing all binding entries with no other parameters.";

      input {

          leaf clear-type {
              type string;
              description "Either one entry or all. V4_ONE or V4_ALL.";
          }

          leaf mac-address {
              type string;
              description "6 byte MAC address.";
          }

          leaf interface {
              type string;
              description "Interface where snooping binding entries need to be cleared.";
          }

          leaf vlan {
              type string;
              description "VLAN associated with snooping binding entries.";
          }

          leaf ip {
              type string;
              description "IPV4 address that needs to be removed.";
          }
      }
      output {
          leaf status {
              type string;
              description
                      " success / failure of deletion of dynamic binding entries";
          }
      }
  }

  rpc clear-dhcpv6-snooping-binding {

    description "RPC for clearing DHCP snooping binding entries. Input can be :
        1. V6_ONE as clear-type for clearing specific binding entry with MAC, interface, VLAN and IP address.
        2. V6_ALL as clear-type for clearing all binding entries with no other parameters.";

      input {

          leaf clear-type {
              type string;
              description "Either one entry or all. V6_ONE or V6_ALL.";
          }

          leaf mac-address {
              type string;
              description "6 byte MAC address.";
          }

          leaf interface {
              type string;
              description "Interface where snooping binding entries need to be cleared.";
          }

          leaf vlan {
              type string;
              description "VLAN associated with snooping binding entries.";
          }

          leaf ip {
              type string;
              description "IPV4 address that needs to be removed.";
          }
      }
      output {
          leaf status {
              type string;
              description
                      " success / failure of deletion of dynamic binding entries";
          }
      }
  }

  rpc clear-dhcp-snooping-statistics{
    description
      "Operation for clearing DHCP Snooping statistics on interface";

    input {
      leaf interface {
        type string;
        description
          "Interface for which clear operation needs to be performed";
      }
    }

    output {
      leaf error {
        type string;
        description
          "Result of RPC Operation";
      }
    }

  }

 rpc clear-dhcpv6-snooping-statistics{
    description
      "Operation for clearing DHCPv6 Snooping statistics on interface";

    input {
      leaf interface {
        type string;
        description
          "Interface for which clear operation needs to be performed";
      }
    }

    output {
      leaf error {
        type string;
        description
          "Result of RPC Operation";
      }
    }
  }

 rpc clear-dhcp-snooping-statistics-detail{
   description
     "Operation for clearing DHCP Snooping statistics on switch";

   output {
     leaf error {
       type string;
       description
         "Result of RPC Operation";
     }
   }
 }

 rpc clear-dhcpv6-snooping-statistics-detail{
   description
     "Operation for clearing DHCPv6 Snooping statistics on switch";

   output {
     leaf error {
       type string;
       description
         "Result of RPC Operation";
     }
   }
 }
}
