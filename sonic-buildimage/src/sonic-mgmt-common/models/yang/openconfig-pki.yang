module openconfig-pki {

  yang-version "1";

  // namespace
  namespace "http://openconfig.net/yang/pki";

  prefix "oc-pki";

  import openconfig-extensions { prefix oc-ext; }
  import openconfig-inet-types { prefix oc-inet; }

  // meta
  organization "OpenConfig working group";

  contact
    "OpenConfig working group
    www.openconfig.net";

  description
    "This module defines configuration and operational state
    data for Public Key Infrastructure";

  oc-ext:openconfig-version "1.2.2";

  revision "2024-01-30" {
    description
      "Add vrf-name leaf";
    reference "1.2.2";
  }
  revision "2023-01-23" {
    description
      "Initial Version";
    reference "1.2.1";
  }

  grouping trust-store-config {
    description
      "Trust Store config";

    leaf "name" {
        type string;
        description
            "Unique name for the trust store";
    }
    leaf-list ca-name{
        type string;
        description
            "List of CA certificates to be added to the trust store";
        min-elements 1;
    }
  }
  grouping trust-store-state {
    description
      "Trust Store state";
  }

    grouping trust-store-top {
    description
      "Trust Store entries variables top level container";

    container trust-stores {
      description
        "Trust Store entries variables enclosing container";

      list trust-store {
        key "name";
        description
          "List of Trust Stores, each comprising of a list of Trust Store
          entries";

        leaf name {
          type leafref {
            path "../config/name";
          }
          description
            "Reference to the name key";
        }

        container config {
          description
            "Trust Store config";
          uses trust-store-config;
        }

        container state {
          config false;
          description
            "Trust Store state information";
          uses trust-store-config;
          uses trust-store-state;
        }
      }
    }
    }

  grouping security-profile-config {
    description
      "Security Profile config";

    leaf "profile-name" {
            type string;
            description
            "Unique name for the security profile";
    }
    leaf "certificate-name" {
        type string;
        description
            "Certificate file name";
    }
    leaf "trust-store" {
        type leafref {
            path "../../../../trust-stores/trust-store/config/name";
        }
        
        description
            "Trust Store Name";
    }
    leaf "revocation-check" {
        type boolean;
        description
            "Require service strictly require revocation checking";
    }
    leaf "peer-name-check" {
        type boolean;
        description
            "Require service to verfiy peer host name matches certificate";
    }
    leaf "key-usage-check" {
        type boolean;
        description
            "Require certificate is being used as specified in certificate";
    }
    leaf-list "cdp-list" {
        type oc-inet:url;
        description
            "A list of CDP's provided in addition to those specified in the certificate";
    }
    leaf-list "ocsp-responder-list" {
        type oc-inet:url;
        description
            "A list of OCSP responders provided in addition to those specified in the certificate";
    }
    leaf "vrf-name" {
      type string {
        pattern "mgmt";
      }
      description
          "mgmt VRF for outbound connections to OCSP responders and/or CDPs";
    }
  }

  grouping security-profile-state {
    description
      "Security Profile state";
  }

    grouping security-profile-top {
    description
      "Security Profile entries variables top level container";

    container security-profiles {
      description
        "Security Profile entries variables enclosing container";

      list security-profile {
        key "profile-name";
        description
          "List of Security Profiles, each comprising of a list of Security Profile
          entries";

        leaf profile-name {
          type leafref {
            path "../config/profile-name";
          }
          description
            "Reference to the name key";
        }

        container config {
          description
            "Security Profile config";
          uses security-profile-config;
        }

        container state {
          config false;
          description
            "Security Profile state information";
          uses security-profile-config;
          uses security-profile-state;
        }
      }
    }
    }
  grouping pki-top {
    description
      "Top level grouping for PKI data and structure";

    container pki {
      description
        "Top level enclosing container for PKI model config
        and operational state data";


      uses security-profile-top;
      uses trust-store-top;
      
    }
  }
    uses pki-top;
}
