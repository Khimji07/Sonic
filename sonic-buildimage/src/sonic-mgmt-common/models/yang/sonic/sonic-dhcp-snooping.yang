module sonic-dhcp-snooping {
    namespace "http://github.com/Azure/sonic-dhcp-snooping";
    prefix dhcp-snooping;
    yang-version 1.1;

    import ietf-yang-types {
        prefix yang;
    }

    import sonic-common {
        prefix scommon;
    }

    import ietf-inet-types {
        prefix inet;
    }

    import sonic-extension {
        prefix sonic-ext;
    }

    import sonic-vlan {
        prefix svlan;
    }

    organization
        "SONiC";

    contact
        "SONiC";

    description
        "SONIC DHCP SNOOPING";

    revision 2021-07-15 {
        description
            "Initial revision.";
    }

    typedef binding {
        type enumeration {
            enum static {
                description "Static binding entry";
            }
            enum dynamic {
                description "Dynamic binding entry";
            }
            enum tentative {
                description "tentative binding entry";
            }
        }
        description "Type of DHCP snooping binding entry";
    }

    rpc clear_dhcp_snooping_binding {
        input {
            leaf binding-param {
                type string;
                description
                        "parameter for deleting either all dynamic binding entries or a specific entry";
            }
        }
        output {
            leaf status {
                type string;
                description
                        " success / failure of deletion of dynamic binding entries";
            }
        }
    }

    rpc clear_dhcpv6_snooping_binding {
        input {
            leaf binding-v6-param {
                type string;
                description
                        "parameter for deleting either all dynamic binding entries or a specific entry";
                }
        }
        output {
            leaf status {
                type string;
                description
                        " success / failure of deletion of dynamic binding entries";
            }
        }
    }

    container sonic-dhcp-snooping {

        container DHCP_SNOOPING {

            list DHCP_SNOOPING_LIST {
                key "id";

                leaf id{
                    type enumeration {
                        enum GLOBAL;
                    }
                    description
                            "global key";
                }

                leaf dhcpv4_admin_enable {
                    type scommon:mode-enable;
                    default disable;
                    description
                        "";
                }
                leaf dhcpv4_verify_mac_address{
                    type scommon:mode-enable;
                    default enable;
                    description
                        "";
                }
                leaf dhcpv6_admin_enable {
                    type scommon:mode-enable;
                    default disable;
                    description
                        "";
                }
                leaf dhcpv6_verify_mac_address {
                    type scommon:mode-enable;
                    default enable;
                    description
                        "";
                }
            }
        }

        container DHCP_SNOOPING_STATIC_BINDING {
            list DHCP_SNOOPING_STATIC_BINDING_LIST {
                key "mac iptype";

                leaf mac {
                    type yang:mac-address;
                    description
                        "MAC address of the static DHCP snooping entry";
                }
                leaf iptype {
                    type inet:ip-version;
                    description
                        "IP version ipv4 or ipv6";
                }
                leaf vlan {
                    type leafref {
                        path "/svlan:sonic-vlan/svlan:VLAN/svlan:VLAN_LIST/svlan:name";
                    }
                    description
                        "";
                }
                leaf interface {
                    type string;
                    description
                        "";
                }
                leaf ip {
                    type inet:ip-address;
                    description
                        "IPv4 or IPv6 address";
                }
            }
        }

        container DHCP_SNOOPING_BINDING {
            sonic-ext:db-name "APPL_DB";
            sonic-ext:key-delim ":";

            config false;
            list DHCP_SNOOPING_BINDING_LIST {
                key "mac ipType";

                leaf mac {
                    type yang:mac-address;
                    description
                        "MAC address of the DHCP snooping entry";
                }
                leaf vlan {
                    type leafref {
                        path "/svlan:sonic-vlan/svlan:VLAN/svlan:VLAN_LIST/svlan:name";
                    }
                    description
                        "";
                }
                leaf intf {
                    type string;
                    description
                        "";
                }
                leaf ipaddress {
                    type inet:ip-address;
                    description
                        "IPv4 or IPv6 address";
                }
                leaf ipType {
                    type inet:ip-version;
                    description
                        "IP version ipv4 or ipv6";
                }
                leaf lease_time {
                    type uint32;
                    units seconds;
                    description
                        "";
                }
                leaf lease_end_time {
                    type uint32;
                    units seconds;
                    description
                        "";
                }
                leaf type {
                    type binding;
                    description
                        "Static or dynamic DHCP binding entry";
                }
            }
        }

        grouping dhcp-snooping-counters {

            leaf errMsgRx {
                type uint64;
            }
            leaf errRxSrcIp {
                type uint64;
            }
            leaf numDhcpPktRcvd {
                type uint64;
            }
            leaf numDhcpPktProc {
                type uint64;
            }
            leaf numDhcpPktFiltered {
                type uint64;
            }
            leaf numDhcpFwd {
                type uint64;
            }
            leaf numReleaseDeclineUnknownErr {
                type uint64;
            }
            leaf numDynBindingAdd {
                type uint64;
            }
            leaf numDynBindingDel {
                type uint64;
            }
            leaf numDhcpPktDropped {
                type uint64;
            }
            leaf numDhcpTxDrops {
                type uint64;
            }
            leaf errMsgBig {
                type uint64;
            }
            leaf errMsgTx {
                type uint64;
            }
            leaf numDhcpPktBindingExists {
                type uint64;
            }
            leaf errRxSrcMac {
                type uint64;
            }
        }

        container DHCP_SNOOPING_STATISTICS_DETAIL {
            sonic-ext:db-name "APPL_DB";
            sonic-ext:key-delim ":";
            config false;
            list DHCP_SNOOPING_STATISTICS_DETAIL_LIST {
                key "ipType";

                leaf ipType {
                    type inet:ip-version;
                    description
                        "IP version ipv4 or ipv6";
                }

                uses dhcp-snooping-counters;
            }
        }

        grouping dhcp-snooping-statistics {
            leaf Interface {
                type string;
                description
                    "Interafce name";
            }
            leaf mac_verify_failures {
                type uint64;
            }
            leaf if_mismatches {
                type uint64;
            }
            leaf server_msgs_on_untrusted {
                type uint64;
            }
            leaf v6_mac_verify_failures {
                type uint64;
            }
            leaf v6_if_mismatches {
                type uint64;
            }
            leaf v6_server_msgs_on_untrusted {
                type uint64;
            }
        }

        container DHCP_SNOOPING_STATISTICS {
            sonic-ext:db-name "APPL_DB";
            sonic-ext:key-delim ":";
            config false;

            list DHCP_SNOOPING_STATISTICS_LIST {
                key Interface;

                uses dhcp-snooping-statistics;
            }
        }
    }
}
