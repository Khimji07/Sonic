module sonic-port-breakout {
    namespace "http://github.com/Azure/sonic-port-breakout";
    prefix sbrkprt;

    import sonic-port {
        prefix prt;
    }

    import sonic-extension {
        prefix sonic-ext;
    }

    organization
        "SONiC";

    contact
        "SONiC";

    description
        "SONiC Port Breakout";

    revision 2023-12-19 {
        description
            "Adding breakout-owner attribute for auto-breakout feature";
    }

    revision 2020-03-12 {
        description
            "Initial revision.";
    }

    container sonic-port-breakout {

        container BREAKOUT_CFG {

            list BREAKOUT_CFG_LIST {

                key "ifname";
                sonic-ext:dependent-on "PORT_LIST";
                sonic-ext:custom-validation ValidateBufferConfigMode;

                leaf ifname {
                    sonic-ext:custom-validation ValidateDpbConfigs;
                    type string {
                        pattern "Ethernet([1-3][0-9]{3}|[1-9][0-9]{2}|[1-9][0-9]|[0-9])|Eth([1-9]/(([1-9][0-9]{0,})|(([1-9][0-9]{0,})/([1-9][0-9]{0,}))))";
                    }
                }

                leaf port {
                    type string;
                }

                leaf brkout_mode {
                    type string;
                }

                leaf lanes {
                    type string;
                }
                leaf source_lanes {
                    type string;
                }
                leaf target_lanes {
                    type string;
                }
                leaf status {
                    type string;
                }
                leaf breakout_owner{
                    type enumeration {
                        enum MANUAL {
                            description
                                "Sets breakout owner as manual";
                        }
                        enum AUTO {
                            description
                                "Sets breakout owner as auto";
                        }
                    }
                    default MANUAL;
                }
            }
        }

        container BREAKOUT_PORTS {

            list BREAKOUT_PORTS_LIST {

                key "ifname";

                leaf ifname {
                    type string {
                        pattern "Ethernet([1-3][0-9]{3}|[1-9][0-9]{2}|[1-9][0-9]|[0-9])|Eth([1-9]/(([1-9][0-9]{0,})|(([1-9][0-9]{0,})/([1-9][0-9]{0,}))))";
                    }
                }

                leaf master {
                    type string;
                }
            }
        }

        container PORT_BREAKOUT {
            sonic-ext:db-name "STATE_DB";
            sonic-ext:key-delim "|";
            config false;
            list PORT_BREAKOUT_LIST {
                key "ifname";
                leaf ifname {
                    type string {
                        pattern "Ethernet([1-3][0-9]{3}|[1-9][0-9]{2}|[1-9][0-9]|[0-9])|Eth([1-9]/(([1-9][0-9]{0,})|(([1-9][0-9]{0,})/([1-9][0-9]{0,}))))";
                    }
                }

                leaf status {
                    type string;
                }
            }
        }
    }

    rpc breakout_dependencies {

        description "RPC for showing dependencies on breakout port
        input is Ethernet interface";

        input {
            leaf ifname {
                type leafref {
                    path "/prt:sonic-port/prt:PORT/prt:PORT_LIST/prt:ifname";
                }
            }
        }

        output {
            leaf-list keys {
                type string;
                description
                    "On success, returns list of dependent table keys";
            }
        }
    }

    rpc breakout_capabilities {

        description "RPC for listing the breakout capabilities of ports
        input is Ethernet interface";

        input {
            leaf ifname {
                type leafref {
                    path "/prt:sonic-port/prt:PORT/prt:PORT_LIST/prt:ifname";
                }
            }
        }

        output {
            list caps {
                leaf port {
                    type string;
                }
                leaf modes {
                    type string;
                }
                leaf defmode {
                    type string;
                }
                leaf pipe {
                    type string;
                }
            }
        }
    }


    rpc breakout_resources {

        description "RPC for listing the breakout resource limits
        and current consumption. For example number of ports supported in the systems or in a pipeline";

        output {
            list pipelines {
                leaf pipe {
                    type string;
                }
                leaf port-count-limit {
                    type string;
                }
                leaf current-port-count {
                    type string;
                }
                leaf front-panel-ports {
                    type string;
                }
            }
            leaf system-port-count-limit {
                type string;
            }
            leaf system-current-port-count {
                type string;
            }
         }
     }
}
