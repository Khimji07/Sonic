module sonic-hostapd {
    namespace "http://github.com/Azure/sonic-hostapd";
    prefix hostapd;
    yang-version 1.1;

    organization
        "SONiC";

    contact
        "SONiC";

    description
        "This module allows configuration of dot1x/hostapd";

    revision 2021-07-13 {
        description
            "Initial revision.";

    }

    container sonic-hostapd {
       container HOSTAPD_GLOBAL_CONFIG_TABLE {
           description
       	      "Global configuration of MAC Authentication Bypass (MAB).";

           list HOSTAPD_GLOBAL_CONFIG_TABLE_LIST {
		key "global";

               leaf global {
                    type enumeration {
                       enum GLOBAL;
                    }
                    description
                       "Configure dot1x/hostapd global configuration.";
               }

               leaf dot1x_system_auth_control {
                  type boolean;
                  description
                     "Indicates whether dot1x/hostapd Enabled/Disabled on the switch.";
               }
           }
       }
    /*
       container HOSTAPD_OPER_PORT_TABLE {
            sonic-ext:db-name "STATE_DB";
            sonic-ext:key-delim "|";
            config false;

            list HOSTAPD_OPER_PORT_TABLE_LIST {
                key "port";

                leaf port {
                   type leafref {
                        path "/prt:sonic-port/prt:PORT/prt:PORT_LIST/prt:ifname";
                   }
                   description
                       "Name of the interface on which PAC port config get applied.";
                 }

                leaf protocol_version {
                    type uint8;
                    description
                        "dot1x protocol version.";
                }

                leaf quiet_period {
                    type uint32 {
		       range 10..65535 {
			   error-message "quiet period value must be in range 10-65535.";
			   error-app-tag quiet-period-invalid;
		       }
                    }
                    units "seconds";
                    description
                        "The initial value of the timer that defines the period
                        during which the Authenticator will not attempt to authenticate the Supplicant.";
                }

                leaf tx_period {
                    type uint8;
                    description
                        "Time time interval between each EAP Request Ids sent to the supplicant.";
                }

                leaf server_timeout {
                    type uint8;
                    description
                        "RADIUS server timeout.";
                }

                leaf max_reqs {
                    type uint8;
                    description
                        "Maximum number of EAP requests (except Req-Ids) to be sent to the supplicant before timing out.";
                }

                leaf max_req_ids {
                    type uint8;
                    description
                        "Maximum number of EAP Req-Ids to be sent to the supplicant before timing out.";
                }
            }
       }

       container HOSTAPD_CLIENT_OPER_TABLE {
            sonic-ext:db-name "STATE_DB";
            sonic-ext:key-delim "|";
            config false;

            list HOSTAPD_CLIENT_OPER_TABLE_LIST {
                key "port mac_addr";

                leaf port {
                   type leafref {
                        path "/prt:sonic-port/prt:PORT/prt:PORT_LIST/prt:ifname";
                   }
                   description
                        "Physical Port.";
                 }

                leaf mac_addr {
                    type yang:mac-address;
                    description
                        "Client MAC.";
                }

		leaf user_name {
                    type string {
                        length 1..31 {
                           error-message "valid length for user name is 1-31.";
                           error-app-tag user-name-invalid;
                        }
                    }
                }
              }
       }

       container HOST_APD_STATS_TABLE {
            sonic-ext:db-name "COUNTERS_DB";
            sonic-ext:key-delim ":";
            config false;

            list HOST_APD_STATS_TABLE_LIST {
                key "mac_address";

                leaf mac_address {
                    type yang:mac-address;
                    description
                        "Client MAC.";
                }

                leaf port {
                   type leafref {
                        path "/prt:sonic-port/prt:PORT/prt:PORT_LIST/prt:ifname";
                   }
                   description
                        "Name of the interface on which PAC port config get applied.";
                }

                leaf dot1xAuthEapolFramesRx {
                    type uint8;
                    description
                        "The number of valid EAPOL frames of any type that have been received by this Authenticator.";
                }

                leaf dot1xAuthEapolFramesTx {
                    type uint8;
                    description
                        "The number of EAPOL frames of any type that have been transmitted by this Authenticator.";
                }

                leaf dot1xAuthEapolStartFramesRx {
                    type uint8;
                    description
                        "The number of EAPOL Start frames that have been received by this Authenticator.";
                }

                leaf dot1xAuthEapolLogoffFramesRx {
                    type uint8;
                    description
                        "The number of EAPOL Logoff frames that have been received by this Authenticator.";
                }

                leaf dot1xAuthEapolRespIdFramesRx {
                    type uint8;
                    description
                        "The number of EAP Resp/Id frames that have been received by this Authenticator.";
                }

                leaf dot1xAuthEapolRespFramesRx {
                    type uint8;
                    description
                        "The number of valid EAP Response frames (other than Resp/Id frames) that have been received by this Authenticator.";
                }

                leaf dot1xAuthEapolReqFramesTx {
                    type uint8;
                    description
                        "The number of EAP Request frames (other than Rq/Id frames) that have been transmitted by this Authenticator.";
                }

                leaf dot1xAuthEapolReqIdFramesTx {
                    type uint8;
                    description
                        "The number of EAP Req/Id frames that have been transmitted by this Authenticator.";
                }

                leaf dot1xAuthInvalidEapolFramesRx {
                    type uint8;
                    description
                        "The number of EAPOL frames that have been received by this Authenticator in which the frame type is not recognized.";
                }

                leaf dot1xAuthEapLengthErrorFramesRx {
                    type uint8;
                    description
                        "The number of EAPOL frames that have been received by this Authenticator in which the Packet Body Length field is invalid.";
                }

                leaf dot1xAuthLastEapolFrameVersion {
                    type uint8;
                    description
                        "The protocol version number carried in the most recently received EAPOL frame.";
                }
             }
        }
    */
    }
}
