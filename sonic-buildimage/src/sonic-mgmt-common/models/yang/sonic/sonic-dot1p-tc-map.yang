module sonic-dot1p-tc-map {
	namespace "http://github.com/Azure/sonic-dot1p-tc-map";
	prefix dot1ptm;

	organization
		"SONiC";

	contact
		"SONiC";

	description
		"SONIC DOT1P_TO_TC_MAP";

	revision 2019-05-15 {
		description
			"Initial revision.";
	}

	container sonic-dot1p-tc-map {	

		container DOT1P_TO_TC_MAP {

			list DOT1P_TO_TC_MAP_LIST {
				key "name";

				leaf name {
        				type string {
                        		pattern '[a-zA-Z0-9]{1}([-a-zA-Z0-9_]{0,31})';
                        		length 1..32;
                			}
				}

				list DOT1P_TO_TC_MAP { //this is list inside list for storing mapping between two fields
					key "dot1p";

        				leaf dot1p {
						type string {
							pattern "[0-7]?"{
								error-message "Invalid Dot1p Priority";
								error-app-tag dot1p-invalid;
							}
						}
					}

					leaf tc_num {
						type string {
							pattern "[0-7]?"{
								error-message "Invalid Traffic Class number";
								error-app-tag tc-num-invalid;
							}
						}
					}
                		}
			}
		}
	}
}
