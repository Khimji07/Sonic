module sonic-port-group {
    namespace "http://github.com/Azure/sonic-port-group";
    prefix port-group;

    import sonic-extension {
        prefix sonic-ext;
    }

    organization
        "SONiC";

    contact
        "SONiC";

    description
        "SONIC port-group";

    revision 2020-07-20 {
        description
            "Initial revision.";
    }

    container sonic-port-group {
        container PORT_GROUP {
            description "Port-group configurations.";

            list PORT_GROUP_LIST {
                key "id";

                leaf id {
                    type string;
                    description
                        "Port-group id";
                }

                leaf speed {
                    type string;
                    description
                        "Port-group member ports speed";
                    must "(count(current()/../../PORT_GROUP_LIST) > 1)" {
                        error-message "Port group is not supported";
                        error-app-tag port-group-unsupported;
                    }
                }
            }
        }
    }
}
