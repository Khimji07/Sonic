module sonic-nht {
  namespace "http://github.com/Azure/sonic-nht";
  prefix sn-nht ;
  yang-version 1.1;

  import sonic-vrf {
    prefix "sonic-vrf";
  }

  organization
    "SONiC";

  contact
    "SONiC";

  description
     "SONIC Nexthop tracking config Global YANG";

  revision 2021-08-19 {
    description
      "Added Yang definition for Nexthop Tracking features.";
  }

  typedef nht-address-family {
    description
      "Nexthop tracking address family type.";
    type enumeration {
      enum IPV4 {
        value 4;
        description
         "The IPv4 protocol as defined in RFC 791.";
      }
      enum IPV6 {
        value 6;
        description
         "The IPv6 protocol as defined in RFC 2460.";
      }
    }
  }

  container sonic-nht {
    description
      "Nexthop tracking configuration table.";

    container NHT_VRF_AF {
      description
        "Nexthop tracking configuration table.";

      list NHT_VRF_AF_LIST {
        description
          "Nexthop tracking configuration table row.";

        key "vrf_name family";

        leaf vrf_name {
          type union {
            type string {
              pattern "default";
            }
            type leafref {
              path "/sonic-vrf:sonic-vrf/sonic-vrf:VRF/sonic-vrf:VRF_LIST/sonic-vrf:vrf_name";
            }
            //error-message "VRF not configured";
            //error-app-tag vrf-name-not-present;
          }
          description
            "VRF instance name.";
        }

        leaf family {
          type nht-address-family ;
          description
             "Address family(IPv4/IPv6)";
        }

        leaf resolve-via-default {
          type  boolean;
          description
            "Enable or disable Nexthop resolution via default route.";
       }

      } //NHT_VRF_AF_LIST
    } //NHT_VRF_AF

  } //sonic-nht
}
