module sonic-buffer-queue {
	namespace "http://github.com/Azure/sonic-buffer-queue";
	prefix bqueue;

	import sonic-extension {
		prefix sonic-ext;
	}

	import sonic-common {
		prefix cmn;
	}

	import sonic-port {
		prefix prt;
	}

	import sonic-buffer-profile {
		prefix bpf;
	}

	organization
		"SONiC";

	contact
		"SONiC";

	description
		"SONIC BUFFER QUEUE";

	revision 2019-05-15 {
		description
			"Initial revision.";
	}


	container sonic-buffer-queue {

		container BUFFER_QUEUE {

			list BUFFER_QUEUE_LIST {
				key "ifname qindex";
				sonic-ext:key-pattern "QUEUE|{ifname}|{qindex}"; //special pattern used for extracting keys from redis-key and populate the yang instance
										   // Total list instances = number(key1) * number(key2) * number(key3)

                                sonic-ext:custom-validation ValidateBufferConfCapability;
                                sonic-ext:custom-validation ValidateBufferConfigsInitilized;
                                sonic-ext:custom-validation ValidateDpbBufferPgDeletion;
                                leaf ifname {
					type leafref {
						path "/prt:sonic-port/prt:PORT/prt:PORT_LIST/prt:ifname";
					}
				}

				leaf qindex {
					type string;
					sonic-ext:custom-validation ValidateRangeIndexOverlap;
					sonic-ext:custom-validation ValidateBufferQindexPattern;
				}

				leaf profile { //Hash reference key
					type leafref {
						path "/bpf:sonic-buffer-profile/bpf:BUFFER_PROFILE/bpf:BUFFER_PROFILE_LIST/bpf:name";
					}
					must "(/cmn:operation/cmn:operation = 'DELETE') or " +
                                                "(not(/bpf:sonic-buffer-profile/bpf:BUFFER_PROFILE/bpf:BUFFER_PROFILE_LIST[bpf:name=current()]/bpf:pool = 'ingress_lossless_pool')) or " +
							"(not(/bpf:sonic-buffer-profile/bpf:BUFFER_PROFILE/bpf:BUFFER_PROFILE_LIST[bpf:name=current()]/bpf:type = 'ingress') and " +
							"not(/bpf:sonic-buffer-profile/bpf:BUFFER_PROFILE/bpf:BUFFER_PROFILE_LIST[bpf:name=current()]/bpf:xoff) and " +
							"not(/bpf:sonic-buffer-profile/bpf:BUFFER_PROFILE/bpf:BUFFER_PROFILE_LIST[bpf:name=current()]/bpf:xon) and " +
							"not(/bpf:sonic-buffer-profile/bpf:BUFFER_PROFILE/bpf:BUFFER_PROFILE_LIST[bpf:name=current()]/bpf:xon_offset))" {
						error-app-tag profile-invalid-for-buffer-queue;
						error-message "Profile config is not valid or Mismatch between Queue and Profile types for buffer-queue";
					}

                                        sonic-ext:custom-validation ValidatePoolTypeMatch;
				}

			}
		}
	}
}
