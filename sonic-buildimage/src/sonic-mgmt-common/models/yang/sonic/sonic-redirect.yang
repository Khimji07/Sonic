module sonic-redirect {
    namespace "http://github.com/Azure/sonic-redirect";
    prefix sredirect;
    yang-version 1.1;

    import sonic-pki {
        prefix spki;
    }

    // meta
    organization
    "SONiC";

    contact
    "SONiC";

    description
    "This module defines configuration and operational state data for SONiC redirect component.";

    revision "2022-12-21" {
      description
      "Initial revision.";
    }

    container sonic-redirect {
        container REDIRECT_SERVER {
           list REDIRECT_SERVER_LIST {
               key "id";
               leaf id {
                    type enumeration {
                        enum default;
                    }
               }
               leaf security_profile {
                   type leafref {
                        path "/spki:sonic-pki/spki:SECURITY_PROFILES/spki:SECURITY_PROFILES_LIST/spki:profile-name";
                   }
               }
           }
        }
    }

}
