module sonic-pms {
    namespace "http://github.com/Azure/sonic-pms";
    prefix spms;
    yang-version 1.1;

    import sonic-extension {
        prefix sonic-ext;
    }

    import sonic-port {
        prefix prt;
    }

    import sonic-portchannel {
        prefix spc;
    }


    organization
        "SONiC";

    contact
        "SONiC";

    description
        "SONiC PMS yang model";

    revision 2021-05-10 {
        description
            "Initial revision.";
    }

    grouping pms_port_config {
        leaf admin_enable {
            type boolean;
            sonic-ext:custom-validation ValidatePmsPacPort;
            description
                "Enable/Disable PMS";
        }

        leaf maximum {
            type uint16 {
                range "1..4097" {
                    error-message "Invalid value.";
                }
            }
            default 1;
            description
                "Set the maximum number of allowed MAC addresses on a port";
        }

        leaf violation {
            type string;
            description
                "PMS violation action";
        }
    }

    container sonic-pms {
        container PMS_PORT {
            list PMS_PORT_LIST {
                key "ifname";

                leaf ifname {
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                    }
                    description
                        "Reference of port on which PMS to be configured.";
                }

                uses pms_port_config;
            }
        }

        container _PMS_PORT_TABLE {
            config false;

            list _PMS_PORT_TABLE_LIST {
                sonic-ext:db-name "ASIC_DB";
                key "ifname";

                leaf ifname {
                    type leafref {
                        path "/prt:sonic-port/prt:PORT/prt:PORT_LIST/prt:ifname";
                    }
                    description
                        "Reference of port on which PMS is configured.";
                }
                leaf curr_address {
                    type uint16;
                    description
                        "total no of MAC address learnt on this port";
                }

                leaf violation_count {
                    type uint32;
                    description
                        "No of times violation has been hit on this port";
                }

            }
        }

    }
}
