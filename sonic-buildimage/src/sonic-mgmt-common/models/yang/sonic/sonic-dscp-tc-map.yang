module sonic-dscp-tc-map {
	namespace "http://github.com/Azure/sonic-dscp-tc-map";
	prefix dtm;

	organization
		"SONiC";

	contact
		"SONiC";

	description
		"SONIC DSCP_TO_TC_MAP";

	revision 2019-05-15 {
		description
			"Initial revision.";
	}

	container sonic-dscp-tc-map {	

		container DSCP_TO_TC_MAP {

			list DSCP_TO_TC_MAP_LIST {
				key "name";

				leaf name {
        				type string {
                        		pattern '[a-zA-Z0-9]{1}([-a-zA-Z0-9_]{0,31})';
                        		length 1..32;
                			}
				}

				list DSCP_TO_TC_MAP { //this is list inside list for storing mapping between two fields
					key "dscp";

					leaf dscp {
						type string {
							pattern "([0-9]|[1-5][0-9]|6[0-3])?" {
								error-message "Invalid DSCP priority";
								error-app-tag dscp-invalid;
							}
						}
					}
					leaf tc_num {
						type string {
							pattern "[0-7]?"{
								error-message "Invalid Traffic Class number";
								error-app-tag tc-num-invalid;
							}
						}
					}
				}

			}
		}
	}
}
