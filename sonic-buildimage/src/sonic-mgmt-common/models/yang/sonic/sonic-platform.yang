module sonic-platform {
    namespace "http://github.com/Azure/sonic-platform";
    prefix spfm;
    yang-version 1.1;

    organization
        "SONiC";

    contact
        "SONiC";

    description
        "SONiC Platform Components";

    revision 2022-05-26 {
        description "Initial revision.";
    }

    container sonic-platform {
        container PSU_INFO {
            config false;

            list PSU_INFO_LIST {
                key "index";

                leaf index {
                    type string;
                    description
                      "PSU index";
                }
                
                leaf input_current {
                    type string;
                    description
                      "Input current in Amps";
                }

                leaf input_power {
                    type string;
                    description
                      "Input power in Watts";
                }

                leaf input_voltage {
                    type string;
                    description
                      "Input voltage in Volts";
                }

                leaf is_replaceable {
                    type boolean;
                    description
                      "PSU is fixed or replaceable";
                }

                leaf led_status {
                    type string;
                    description
                      "State of the PSU status LED";
                }
                
                leaf mfr_id {
                    type string;
                    description
                      "Manufacturer Id of PSU";
                }
                leaf model {
                    type string;
                    description
                      "PSU model name";
                }

                leaf name {
                    type string;
                    description
                      "PSU name";
                }

                leaf num_fans {
                    type string;
                    description
                      "Number of fan modules available on the PSU";
                }

                leaf output_current {
                    type string;
                    description
                      "Output current in Amps";
                }

                leaf output_power {
                    type string;
                    description
                      "Output power in Watts";
                }

                leaf output_voltage {
                    type string;
                    description
                      "Output voltage in Volts";
                }

                leaf presence {
                    type boolean;
                    description
                      "PSU presence check";
                }

                leaf serial {
                    type string;
                    description
                      "PSU serial number";
                }

                leaf status {
                    type boolean;
                    description
                      "Operational state of PSU";
                }

                leaf type {
                    type string;
                    description
                      "PSU type AC/DC";
                }
            }
        }
        container FAN_INFO {
            config false;

            list FAN_INFO_LIST {
                key "index";

                leaf index {
                    type string;
                    description
                      "FAN index in the list";
                }

                leaf direction {
                    type string;
                    description
                      "Fan Airflow direction (Intake/Exhaust)";
                }

                leaf drawer_name {
                    type string;
                    description
                      "FAN Tray name";
                }

                leaf is_replaceable {
                    type boolean;
                    description
                      "FAN is fixed or replaceable";
                }

                leaf led_status {
                    type string;
                    description
                      "State of the FAN status LED";
                }

                leaf model {
                    type string;
                    description
                      "Model/Part number of the fan";
                }

                leaf name {
                    type string;
                    description
                      "Name of the fan";
                }

                leaf presence {
                    type boolean;
                    description
                      "Fan presence check";
                }

                leaf serial {
                    type string;
                    description
                      "Serial number of the fan";
                }

                leaf speed {
                    type string;
                    description
                      "Fan speed in RPM";
                }

                leaf speed_target {
                    type string;
                    description
                      "Expected speed of the fan in percentage";
                }

                leaf speed_tolerance {
                    type string;
                    description
                      "Speed tolerance of the fan in percentage of variance from target speed";
                }

                leaf status {
                    type boolean;
                    description
                      "Operational state of Fan";
                }
            }
        }

        container TEMPERATURE_INFO {
            config false;            

            list TEMPERATURE_INFO_LIST {
                key "index";

                leaf index {
                    type string;
                    description
                      "Sensor index in the list";
                }

                leaf alarms {
                    type string;
                    description
                      "Active alarms info";
                }

                leaf critical_high_threshold {
                    type string;
                    description
                      "High critical threshold of sensor";
                }

                leaf critical_low_threshold {
                    type string;
                    description
                      "Low critical threshold of sensor";
                }

                leaf high_threshold {
                    type string;
                    description
                      "High threshold of sensor";
                }

                leaf is_replaceable {
                    type boolean;
                    description
                      "Sensor is fixed or replaceable";
                }

                leaf low_threshold {
                    type string;
                    description
                      "Low threshold of sensor";
                }

                leaf maximum_temperature {
                    type string;
                    description
                      "Temperature upper limit of sensor";
                }

                leaf minimum_temperature {
                    type string;
                    description
                      "Temperature lower limit of sensor";
                }

                leaf name {
                    type string;
                    description
                      "Name of the sensor";
                }

                leaf temperature {
                    type string;
                    description
                      "Current temperature reading of sensor in degrees C";
                }

            }
        }

        container I2CERROR_STATS {
            config false;

            list I2CERROR_STATS_LIST {
                key "name";

                leaf name {
                    type string;
                    description
                      "peripheral device name";
                }


                leaf dev_addr {
                    type string;
                    description
                      "I2C peripheral device adapter and address in the form of <adapter>-00<i2c-addr-hex>";
                }

                leaf eio {
                    type uint64;
                    description
                      "Number of input/output or transaction failed errors";
                }

                leaf etimedout {
                    type uint64;
                    description
                      "Number of transaction timeout errors";
                }

                leaf ebusy {
                    type uint64;
                    description
                      "Number of SMBus busy errors";
                }

                leaf enxio {
                    type uint64;
                    description
                      "Number of no response or NACK errors";
                }

                leaf einval {
                    type uint64;
                    description
                      "Number of invalid argument errors";
                }

                leaf eagain {
                    type uint64;
                    description
                      "Number of bus arbiteration lost errors";
                }

                leaf eopnotsupp {
                    type uint64;
                    description
                      "Number of unsupported operation errors";
                }

                leaf eproto {
                    type uint64;
                    description
                      "Number of protocol errors";
                }

                leaf timestamp {
                     type string;
                     description
                       "Displays the date/timestamp of i2c-error stats.";
                }
            }
        }
    }
}
