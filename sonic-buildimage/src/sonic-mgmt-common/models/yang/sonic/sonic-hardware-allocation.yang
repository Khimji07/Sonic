module sonic-hardware-allocation {
    namespace "http://github.com/Azure/sonic-hardware-allocation";
    prefix shw;
    yang-version 1.1;

    import sonic-extension {
        prefix sonic-ext;
    }

    organization
        "SONiC";

    contact
        "SONiC";

    description
        "SONIC Hardware Allocation";

    revision 2021-09-02 {
        description
            "Initial revision.";
    }

    typedef acl-stage {
        description "Feature Binding stages";
        type enumeration {
            enum INGRESS;
            enum EGRESS;
        }
    }

    typedef field-value {
        description "Key profile field is included or not";
        type enumeration {
            enum Y;
            enum N;
        }
    }

    container sonic-hardware-allocation {
        container HARDWARE_ALLOCATION {
            description "Table to control ASIC parameters of different features like ACL.";
            list HARDWARE_ALLOCATION_LIST {
                key "resource-type stage";
                sonic-ext:custom-validation ValidateKeyProfileSupported;
                max-elements 2;

                leaf resource-type {
                    type enumeration {
                        enum TCAM;
                    }
                }

                leaf stage {
                    type acl-stage;
                }

                leaf L2_ACL {
                    when "((current()/../resource-type = 'TCAM') and ((current()/../stage = 'INGRESS') or (current()/../stage = 'EGRESS')))";
                    type string {
                        pattern '([a-zA-Z0-9_-]+)\|([1-9]x?[1-9][0-9]{0,4})*';
                    }
                    description "Key-profile and its TCAM allocation size for the feature L2_ACL.
                        It is in the format <ProfileName>|<Size>. Size can be empty as its optional.";
                }

                leaf L3_ACL {
                    when "((current()/../resource-type = 'TCAM') and ((current()/../stage = 'INGRESS') or (current()/../stage = 'EGRESS')))";
                    type string {
                        pattern '([a-zA-Z0-9_-]+)\|([1-9]x?[1-9][0-9]{0,4})*';
                    }
                    description "Key-profile and its TCAM allocation size for the feature L3_ACL.
                        It is in the format <ProfileName>|<Size>. Size can be empty as its optional.";
                }

                leaf L3V6_ACL {
                    when "((current()/../resource-type = 'TCAM') and ((current()/../stage = 'INGRESS') or (current()/../stage = 'EGRESS')))";
                    type string {
                        pattern '([a-zA-Z0-9_-]+)\|([1-9]x?[1-9][0-9]{0,4})*';
                    }
                    description "Key-profile and its TCAM allocation size for the feature L3V6_ACL.
                        It is in the format <ProfileName>|<Size>. Size can be empty as its optional.";
                }

                leaf QOS_FBS {
                    when "((current()/../resource-type = 'TCAM') and ((current()/../stage = 'INGRESS') or (current()/../stage = 'EGRESS')))";
                    type string {
                        pattern '([a-zA-Z0-9_-]+)\|([1-9]x?[1-9][0-9]{0,4})*';
                    }
                    description "Key-profile and its TCAM allocation size for the feature QOS_FBS.
                        It is in the format <ProfileName>|<Size>. Size can be empty as its optional.";
                }

                leaf MONITORING_FBS {
                    when "((current()/../resource-type = 'TCAM') and ((current()/../stage = 'INGRESS') or (current()/../stage = 'EGRESS')))";
                    type string {
                        pattern '([a-zA-Z0-9_-]+)\|([1-9]x?[1-9][0-9]{0,4})*';
                    }
                    description "Key-profile and its TCAM allocation size for the feature MONITORING_FBS.
                        It is in the format <ProfileName>|<Size>. Size can be empty as its optional.";
                }

                leaf FORWARDING_FBS {
                    when "((current()/../resource-type = 'TCAM') and ((current()/../stage = 'INGRESS') or (current()/../stage = 'EGRESS')))";
                    type string {
                        pattern '([a-zA-Z0-9_-]+)\|([1-9]x?[1-9][0-9]{0,4})*';
                    }
                    description "Key-profile and its TCAM allocation size for the feature FORWARDING_FBS.
                        It is in the format <ProfileName>|<Size> or <ProfileName>|<NxSize>. 
                        Size and NxSize can be empty as its optional.";
                }
            }
        }

        container CURRENT_ACL_KEY_PROFILE_TABLE {
            sonic-ext:db-name "STATE_DB";
            config false;
            list CURRENT_ACL_KEY_PROFILE_TABLE_LIST {
                key "stage";
                max-elements 2;

                leaf stage {
                    type acl-stage;
                }

                leaf L2_ACL {
                    when "((current()/../stage = 'INGRESS') or (current()/../stage = 'EGRESS'))";
                    type string {
                        pattern '([a-zA-Z0-9_-]+)\|([1-9][0-9]{0,4})';
                    }
                    description "Key-profile and its source for the feature L2_ACL.
                        It is in the format <ProfileName>|<ProfileSource>.";
                }

                leaf L3_ACL {
                    when "((current()/../stage = 'INGRESS') or (current()/../stage = 'EGRESS'))";
                    type string {
                        pattern '([a-zA-Z0-9_-]+)\|([1-9][0-9]{0,4})';
                    }
                    description "Key-profile and its source for the feature L3_ACL.
                        It is in the format <ProfileName>|<ProfileSource>.";
                }

                leaf L3V6_ACL {
                    when "((current()/../stage = 'INGRESS') or (current()/../stage = 'EGRESS'))";
                    type string {
                        pattern '([a-zA-Z0-9_-]+)\|([1-9][0-9]{0,4})';
                    }
                    description "Key-profile and its source for the feature L3V6_ACL.
                        It is in the format <ProfileName>|<ProfileSource>.";
                }

                leaf QOS_FBS {
                    when "((current()/../stage = 'INGRESS') or (current()/../stage = 'EGRESS'))";
                    type string {
                        pattern '([a-zA-Z0-9_-]+)\|([1-9][0-9]{0,4})';
                    }
                    description "Key-profile and its source for the feature QOS_FBS.
                        It is in the format <ProfileName>|<ProfileSource>.";
                }

                leaf MONITORING_FBS {
                    when "((current()/../stage = 'INGRESS') or (current()/../stage = 'EGRESS'))";
                    type string {
                        pattern '([a-zA-Z0-9_-]+)\|([1-9][0-9]{0,4})';
                    }
                    description "Key-profile and its source for the feature MONITORING_FBS.
                        It is in the format <ProfileName>|<ProfileSource>.";
                }

                leaf FORWARDING_FBS {
                    when "((current()/../stage = 'INGRESS') or (current()/../stage = 'EGRESS'))";
                    type string {
                        pattern '([a-zA-Z0-9_-]+)\|([1-9][0-9]{0,4})';
                    }
                    description "Key-profile and its source for the feature FORWARDING_FBS.
                        It is in the format <ProfileName>|<ProfileSource>."; 
                }
            }
        }

        container ACL_KEY_PROFILE_DETAILS_TABLE {
            sonic-ext:db-name "STATE_DB";
            sonic-ext:key-delim "|";
            config false;
            list ACL_KEY_PROFILE_DETAILS_TABLE_LIST {
                key "feature key-profile stage";
                max-elements 8;
                leaf feature {
                    type enumeration {
                        enum L2_ACL;
                        enum L3_ACL;
                        enum L3V6_ACL;
                        enum FBS;
                    }
                }

                leaf key-profile {
                    type string {
                        pattern '[a-zA-Z0-9_-]+';
                    }
                    description "Key-profile associated to the feature.";
                }

                leaf stage {
                    type acl-stage;
                    description "Stage where the key-profile will be used by feature.";
                }

                leaf ACL_PRE_INGRESS_EM_USER_META_DATA_0 {
                    type uint16;
                    description "User meta data used for the Key-profile.";
                }

                leaf IN_PORTS {
                    type field-value;
                    default 'N';
                    description "Incoming Ports field is included or not in the Key-profile.";
                }

                leaf ETHER_TYPE {
                    type field-value;
                    default 'N';
                    description "EtherType field is included or not in the Key-profile.";
                }

                leaf VLAN {
                    type field-value;
                    default 'N';
                    description "Vlan field is included or not in the Key-profile.";
                }

                leaf SRC_MAC {
                    type field-value;
                    default 'N';
                    when "(current()/../feature = 'L2_ACL') or (current()/../feature = 'FBS')";
                    description "Source Mac field is included or not in the Key-profile.";
                }

                leaf DST_MAC {
                    type field-value;
                    default 'N';
                    when "(current()/../feature = 'L2_ACL') or (current()/../feature = 'FBS')";
                    description "Destination Mac field is included or not in the Key-profile.";
                }

                leaf PCP {
                    type field-value;
                    default 'N';
                    when "(current()/../feature = 'L2_ACL') or (current()/../feature = 'FBS')";
                    description "PCP field is included or not in the Key-profile.";
                }

                leaf DEI {
                    type field-value;
                    default 'N';
                    when "(current()/../feature = 'L2_ACL') or (current()/../feature = 'FBS')";
                    description "DEI field is included or not in the Key-profile.";
                }

                leaf IP_PROTOCOL {
                    type field-value;
                    default 'N';
                    when "(current()/../feature = 'L3_ACL') or (current()/../feature = 'L3V6_ACL') or (current()/../feature = 'FBS')";
                    description "IP_PROTOCOL field is included or not in the Key-profile.";
                }

                leaf DSCP {
                    type field-value;
                    default 'N';
                    when "(current()/../feature = 'L3_ACL') or (current()/../feature = 'L3V6_ACL') or (current()/../feature = 'FBS')";
                    description "DSCP field is included or not in the Key-profile.";
                }

                leaf SRC_IP {
                    type field-value;
                    default 'N';
                    when "(current()/../feature = 'L3_ACL') or (current()/../feature = 'FBS')";
                    description "Source IP field is included or not in the Key-profile.";
                }

                leaf DST_IP {
                    type field-value;
                    default 'N';
                    when "(current()/../feature = 'L3_ACL') or (current()/../feature = 'FBS')";
                    description "Destination IP field is included or not in the Key-profile.";
                }

                leaf SRC_IPV6 {
                    type field-value;
                    default 'N';
                    when "(current()/../feature = 'L3V6_ACL') or (current()/../feature = 'FBS')";
                    description "Source IPv6 field is included or not in the Key-profile.";
                }

                leaf DST_IPV6 {
                    type field-value;
                    default 'N';
                    when "(current()/../feature = 'L3V6_ACL') or (current()/../feature = 'FBS')";
                    description "Destination IPv6 field is included or not in the Key-profile.";
                }

                leaf TCP_FLAGS {
                    type field-value;
                    default 'N';
                    when "((current()/../feature = 'L3_ACL') or (current()/../feature = 'L3V6_ACL') or (current()/../feature = 'FBS'))";
                    must "current()/../IP_PROTOCOL = 'Y'" {
                        error-app-tag ip-protocol-not-tcp; 
                        error-message "TCP_FLAGS field can be included only when IP_PROTOCOL field is included";
                    }
                    description "TCP flags field is included or not in the Key-profile.";
                }

                leaf ICMP_TYPE {
                    type field-value;
                    default 'N';
                    when "((current()/../feature = 'L3_ACL') or (current()/../feature = 'L3V6_ACL') or (current()/../feature = 'FBS'))";
                    must "current()/../IP_PROTOCOL = 'Y'" {
                        error-app-tag ip-protocol-not-icmp-or-icmpv6;
                        error-message "ICMP_TYPE field can be included only when IP_PROTOCOL field is included";
                    }
                    description "ICMP Type field is included or not in the Key-profile.";
                }

                leaf ICMP_CODE {
                    type field-value;
                    default 'N';
                    when "((current()/../feature = 'L3_ACL') or (current()/../feature = 'L3V6_ACL') or (current()/../feature = 'FBS'))";
                    must "current()/../IP_PROTOCOL = 'Y'" {
                        error-app-tag ip-protocol-not-icmp-or-icmpv6;
                        error-message "ICMP_CODE field can be included only when IP_PROTOCOL field is included";
                    }
                    description "ICMP Code field is included or not in the Key-profile.";
                }

                leaf L4_SRC_PORT {
                    type field-value;
                    default 'N';
                    when "((current()/../feature = 'L3_ACL') or (current()/../feature = 'L3V6_ACL') or (current()/../feature = 'FBS'))";
                    must "current()/../IP_PROTOCOL = 'Y'" {
                        error-app-tag ip-protocol-not-tcp-or-udp;
                        error-message "L4_SRC_PORT field can be included only when IP_PROTOCOL field is included";
                    }
                    description "L4 Source Port field is included or not in the Key-profile.";
                }

                leaf L4_SRC_PORT_RANGE {
                    type field-value;
                    default 'N';
                    when "((current()/../feature = 'L3_ACL') or (current()/../feature = 'L3V6_ACL') or (current()/../feature = 'FBS'))";
                    must "current()/../IP_PROTOCOL = 'Y'" {
                        error-app-tag ip-protocol-not-tcp-or-udp;
                        error-message "L4_SRC_PORT_RANGE field can be included only when IP_PROTOCOL field is included";
                    }
                    description "L4 Source Port Range field is included or not in the Key-profile.";
                }

                leaf L4_DST_PORT {
                    type field-value;
                    default 'N';
                    when "((current()/../feature = 'L3_ACL') or (current()/../feature = 'L3V6_ACL') or (current()/../feature = 'FBS'))";
                    must "current()/../IP_PROTOCOL = 'Y'" {
                        error-app-tag ip-protocol-not-tcp-or-udp;
                        error-message "L4_DST_PORT field can be included only when IP_PROTOCOL field is included";
                    }
                    description "L4 Destination Port field is included or not in the Key-profile.";
                }

                leaf L4_DST_PORT_RANGE {
                    type field-value;
                    default 'N';
                    when "((current()/../feature = 'L3_ACL') or (current()/../feature = 'L3V6_ACL') or (current()/../feature = 'FBS'))";
                    must "current()/../IP_PROTOCOL = 'Y'" {
                        error-app-tag ip-protocol-not-tcp-or-udp;
                        error-message "L4_DST_PORT_RANGE field can be included only when IP_PROTOCOL field is included";
                    }
                    description "L4 Destination Port Range field is included or not in the Key-profile.";
                }
            }
        }
    }
}
