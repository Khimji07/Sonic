module sonic-debugsh {
    namespace "http://github.com/Azure/sonic-debugsh";
    prefix debugsh;
    yang-version 1.1;

    organization
        "SONiC";

    contact
        "SONiC";

    description
        "SONiC yang for debug shell.";

    revision 2021-07-15 {
        description
            "Initial revision.";
    }

    rpc exec-debugsh {
        description "RPC for executing a debug shell command.";

        input {
            leaf backend {
                type string;
                description "The backend daemon handling this command.";
            }
            leaf-list token {
                type string;
                description "The command tokens.";
            }
        }

        output {
            leaf-list output {
                type string;
                description "The output from backend.";
            }
        }
    }

    rpc option-debugsh {
        description "RPC for setting a debug shell option.";

        input {
            leaf name {
                type string;
                description "The option name.";
            }
            leaf-list value {
                type string;
                description "The option values.";
            }
        }
    }
}
