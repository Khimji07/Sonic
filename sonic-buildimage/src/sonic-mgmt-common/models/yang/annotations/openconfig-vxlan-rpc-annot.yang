module openconfig-vxlan-rpc-annot {
    yang-version "1";

    namespace "http://openconfig.net/yang/vxlan-rpc-annot";
    prefix "oc-vxlan-rpc-annot";

    import sonic-extensions { prefix sonic-ext; }
    import openconfig-vxlan-rpc { prefix oc-vxlan-rpc; }

    // meta
    organization
        "OCP SONiC Subproject";

    contact
        "OCP SONiC Subproject Working Group
        https://github.com/Azure/SONiC";

    description
        "SONIC vxlan";

	revision "2020-10-08" {
		description
			"Initial revision";
		reference "0.1.0";
	}

    deviation /oc-vxlan-rpc:clear-vxlan-statistics {
        deviate add {
	        sonic-ext:rpc-callback "rpc_clear_oc_vxlan_statistics";
        }
    }
}
