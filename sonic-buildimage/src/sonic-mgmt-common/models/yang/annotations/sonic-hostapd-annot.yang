module sonic-hostapd-annot {
    namespace "http://github.com/Azure/sonic-hostapd-annot";
    prefix hostapd-annot;
    yang-version 1.1;

    import sonic-extensions { prefix sonic-ext; }
    import sonic-hostapd { prefix shostapd; }

    deviation /shostapd:sonic-hostapd {
        deviate add {
            sonic-ext:user-role-priv "write:secadmin";
        }
    }
}
