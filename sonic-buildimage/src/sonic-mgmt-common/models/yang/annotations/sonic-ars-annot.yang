module sonic-ars-annot {

    yang-version "1.1";

    namespace "http://openconfig.net/yang/annotation/sars-annot";
    prefix "sars-annot";

    import sonic-extensions { prefix sonic-ext; }
    import sonic-ars { prefix sn-ars; }

    deviation /sn-ars:clear-nhg-statistics {
        deviate add {
	    sonic-ext:rpc-callback "rpc_sonic_clear_nhg_counters";
        }
    }
}
