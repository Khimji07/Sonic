module openconfig-bfd-annot {

    yang-version "1.1";

    namespace "http://openconfig.net/yang/bfd-annot";
    prefix "oc-bfd-annot";

    import sonic-extensions { prefix sonic-ext; }
    import openconfig-bfd { prefix oc-bfd; }
    import openconfig-bfd-ext { prefix oc-bfd-ext; }

    // meta
    organization
       "SONiC";

    contact
       "SONiC";

    description
       "SONIC BFD";

    revision 2019-12-11 {
       description
          "Initial revision.";
    }

    deviation /oc-bfd:bfd {
      deviate add {
        sonic-ext:user-role-priv "write:netadmin";
      }
    }

    deviation /oc-bfd:bfd/oc-bfd-ext:bfd-shop-sessions/oc-bfd-ext:single-hop {
      deviate add {
        sonic-ext:key-transformer "bfd_shop_tbl_key_xfmr";
        sonic-ext:table-transformer "bfd_shop_session_tbl_xfmr";
      }
    }

    deviation /oc-bfd:bfd/oc-bfd-ext:bfd-mhop-sessions/oc-bfd-ext:multi-hop {
      deviate add {
        sonic-ext:key-transformer "bfd_mhop_tbl_key_xfmr";
        sonic-ext:table-transformer "bfd_mhop_session_tbl_xfmr";
      }
    }

    deviation /oc-bfd:bfd/oc-bfd-ext:bfd-shop-sessions/oc-bfd-ext:single-hop/oc-bfd-ext:state {
      deviate add {
        sonic-ext:subtree-transformer "bfd_shop_state_xfmr";
      }
    }

    deviation /oc-bfd:bfd/oc-bfd-ext:bfd-mhop-sessions/oc-bfd-ext:multi-hop/oc-bfd-ext:state {
      deviate add {
        sonic-ext:subtree-transformer "bfd_mhop_state_xfmr";
      }
    }

    deviation /oc-bfd:bfd/oc-bfd-ext:bfd-shop-sessions/oc-bfd-ext:single-hop/oc-bfd-ext:config/oc-bfd-ext:remote-address {
        deviate add {
            sonic-ext:field-name "remote-address";
            sonic-ext:field-transformer "bfd_shop_remoteaddr_fld_xfmr";
        }
    }

    deviation /oc-bfd:bfd/oc-bfd-ext:bfd-shop-sessions/oc-bfd-ext:single-hop/oc-bfd-ext:config/oc-bfd-ext:vrf {
        deviate add {
            sonic-ext:field-name "vrf";
            sonic-ext:field-transformer "bfd_shop_vrf_fld_xfmr";
        }
    }

    deviation /oc-bfd:bfd/oc-bfd-ext:bfd-shop-sessions/oc-bfd-ext:single-hop/oc-bfd-ext:config/oc-bfd-ext:interface {
        deviate add {
            sonic-ext:field-name "interface";
            sonic-ext:field-transformer "bfd_shop_interface_fld_xfmr";
        }
    }

    deviation /oc-bfd:bfd/oc-bfd-ext:bfd-shop-sessions/oc-bfd-ext:single-hop/oc-bfd-ext:config/oc-bfd-ext:local-address {
        deviate add {
            sonic-ext:field-name "local-address";
            sonic-ext:field-transformer "bfd_mhop_localaddr_fld_xfmr";
        }
    }

    deviation /oc-bfd:bfd/oc-bfd-ext:bfd-mhop-sessions/oc-bfd-ext:multi-hop/oc-bfd-ext:config/oc-bfd-ext:remote-address {
        deviate add {
            sonic-ext:field-name "remote-address";
            sonic-ext:field-transformer "bfd_mhop_remoteaddr_fld_xfmr";
        }
    }

    deviation /oc-bfd:bfd/oc-bfd-ext:bfd-mhop-sessions/oc-bfd-ext:multi-hop/oc-bfd-ext:config/oc-bfd-ext:vrf {
        deviate add {
            sonic-ext:field-name "vrf";
            sonic-ext:field-transformer "bfd_mhop_vrf_fld_xfmr";
        }
    }

    deviation /oc-bfd:bfd/oc-bfd-ext:bfd-mhop-sessions/oc-bfd-ext:multi-hop/oc-bfd-ext:config/oc-bfd-ext:interface {
        deviate add {
            sonic-ext:field-name "interface";
            sonic-ext:field-transformer "bfd_mhop_interface_fld_xfmr";
        }
    }

    deviation /oc-bfd:bfd/oc-bfd-ext:bfd-mhop-sessions/oc-bfd-ext:multi-hop/oc-bfd-ext:config/oc-bfd-ext:local-address {
        deviate add {
            sonic-ext:field-name "local-address";
            sonic-ext:field-transformer "bfd_mhop_localaddr_fld_xfmr";
        }
    }

    deviation /oc-bfd:bfd/oc-bfd-ext:bfd-profile/oc-bfd-ext:profile {
        deviate add {
	    sonic-ext:table-name "BFD_PROFILE";
            //sonic-ext:table-transformer "bfd_profile_tbl_xfmr";
	    sonic-ext:key-transformer "bfd_profile_tbl_key_xfmr";
      }
    }

    deviation /oc-bfd:bfd/oc-bfd-ext:bfd-profile/oc-bfd-ext:profile/oc-bfd-ext:state {
      deviate add {
        sonic-ext:subtree-transformer "bfd_profile_state_xfmr";
      }
    }

    deviation /oc-bfd:bfd/oc-bfd-ext:bfd-profile/oc-bfd-ext:profile/oc-bfd-ext:config/oc-bfd-ext:profile-name {
        deviate add {
            sonic-ext:field-name "profile-name";
            sonic-ext:field-transformer "bfd_profile_name_fld_xfmr";
        }
    }
}
