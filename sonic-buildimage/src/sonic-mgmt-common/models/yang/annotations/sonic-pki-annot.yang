module sonic-pki-annot {

    yang-version "1";

    namespace "http://openconfig.net/yang/annotation/sonic-pki-annot";
    prefix "sonic-pki-annot";

    import sonic-pki { prefix sonic-pki; }
    import sonic-extensions { prefix sonic-ext; }

    deviation /sonic-pki:sonic-pki {
        deviate add {
            sonic-ext:user-role-priv "write:secadmin; rpc:secadmin;";
        }
    }
}
