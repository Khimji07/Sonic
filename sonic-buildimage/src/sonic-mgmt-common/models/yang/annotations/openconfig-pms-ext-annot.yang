module openconfig-pms-ext-annot {
    yang-version "1";

    namespace "http://openconfig.net/yang/annotation/openconfig-pms-ext-annot";
    prefix "oc-pms-ext-annot";

    import sonic-extensions { prefix sonic-ext; }
    import openconfig-pms-ext { prefix oc-pms-ext; }

    // meta
    organization
       "SONiC";

    contact
       "SONiC";

    description
       "SONIC PMS";

    revision 2021-05-13 {
       description
          "Initial revision.";
    }

	deviation /oc-pms-ext:port-security {
		deviate add {
                        sonic-ext:user-role-priv "write:secadmin";
		}
    }

	deviation /oc-pms-ext:port-security/oc-pms-ext:interfaces/oc-pms-ext:interface {
		deviate add {
			sonic-ext:table-name "PMS_PORT";
		}
    }

	deviation /oc-pms-ext:port-security/oc-pms-ext:interfaces/oc-pms-ext:interface/oc-pms-ext:config/oc-pms-ext:admin-enable {
		deviate add {
			sonic-ext:field-name "admin_enable";
		}
	}

    deviation /oc-pms-ext:port-security/oc-pms-ext:interfaces/oc-pms-ext:interface/oc-pms-ext:config/oc-pms-ext:violation {
        deviate add {
            sonic-ext:field-transformer "pms_port_table_violation_xfmr";
        }
    }

    deviation /oc-pms-ext:port-security/oc-pms-ext:interfaces/oc-pms-ext:interface/oc-pms-ext:config/oc-pms-ext:name {
        deviate add {
            sonic-ext:field-transformer "pms_port_table_ifname_xfmr";
        }
    }

	deviation /oc-pms-ext:port-security/oc-pms-ext:interfaces/oc-pms-ext:interface/oc-pms-ext:state/oc-pms-ext:admin-enable {
		deviate add {
			sonic-ext:field-name "admin_enable";
		}
	}


    deviation /oc-pms-ext:port-security/oc-pms-ext:interfaces/oc-pms-ext:interface/oc-pms-ext:state/oc-pms-ext:oper-info {
        deviate add {
            sonic-ext:db-name "ASIC_DB";
            sonic-ext:table-name "PMS_PORT";
        }
    }

	deviation /oc-pms-ext:port-security/oc-pms-ext:interfaces/oc-pms-ext:interface/oc-pms-ext:state/oc-pms-ext:oper-info/oc-pms-ext:fdb-count {
		deviate add {
			sonic-ext:field-name "fdb_count";
		}
	}

	deviation /oc-pms-ext:port-security/oc-pms-ext:interfaces/oc-pms-ext:interface/oc-pms-ext:state/oc-pms-ext:oper-info/oc-pms-ext:violation-count {
		deviate add {
			sonic-ext:field-name "violation_count";
		}
	}


    deviation /oc-pms-ext:port-security/oc-pms-ext:interfaces/oc-pms-ext:interface/oc-pms-ext:state/oc-pms-ext:violation {
        deviate add {
            sonic-ext:field-transformer "pms_port_table_violation_xfmr";
        }
    }


}
