module openconfig-copp-ext-annot {

    yang-version "1";

    namespace "http://openconfig.net/yang/annotation/oc-copp-annot";
    prefix "oc-copp-annot";

    import openconfig-copp-ext { prefix oc-copp; }
    import sonic-extensions { prefix sonic-ext; }

    deviation /oc-copp:copp {
      deviate add {
                  sonic-ext:user-role-priv "write:netadmin";
      }
    }

    deviation /oc-copp:copp/oc-copp:copp-groups/oc-copp:copp-group {
      deviate add {
		  sonic-ext:table-name "COPP_GROUP";
      }
    }

    // COPP-GROUP CONFIG
    deviation /oc-copp:copp/oc-copp:copp-groups/oc-copp:copp-group/oc-copp:config/oc-copp:name {
      deviate add {
		  sonic-ext:field-transformer "copp_name_field_xfmr";
      }
    }

    deviation /oc-copp:copp/oc-copp:copp-groups/oc-copp:copp-group/oc-copp:config/oc-copp:trap-priority {
      deviate add {
		  sonic-ext:field-name "trap_priority";
      }
    }

    deviation /oc-copp:copp/oc-copp:copp-groups/oc-copp:copp-group/oc-copp:config/oc-copp:trap-action {
      deviate add {
		  sonic-ext:field-transformer "copp_trap_action_xfmr";
		  sonic-ext:field-name "trap_action";
      }
    }

    deviation /oc-copp:copp/oc-copp:copp-groups/oc-copp:copp-group/oc-copp:config/oc-copp:meter-type {
      deviate add {
		  sonic-ext:field-transformer "copp_meter_type_xfmr";
		  sonic-ext:field-name "meter_type";
      }
    }

    deviation /oc-copp:copp/oc-copp:copp-groups/oc-copp:copp-group/oc-copp:config/oc-copp:mode {
      deviate add {
		  sonic-ext:field-transformer "copp_mode_xfmr";
		  sonic-ext:field-name "mode";
      }
    }

    deviation /oc-copp:copp/oc-copp:copp-groups/oc-copp:copp-group/oc-copp:config/oc-copp:red-action {
      deviate add {
		  sonic-ext:field-transformer "copp_red_action_xfmr";
		  sonic-ext:field-name "red_action";
      }
    }

    deviation /oc-copp:copp/oc-copp:copp-groups/oc-copp:copp-group/oc-copp:config/oc-copp:yellow-action {
      deviate add {
		  sonic-ext:field-transformer "copp_yellow_action_xfmr";
		  sonic-ext:field-name "yellow_action";
      }
    }

    deviation /oc-copp:copp/oc-copp:copp-groups/oc-copp:copp-group/oc-copp:config/oc-copp:green-action {
      deviate add {
		  sonic-ext:field-transformer "copp_green_action_xfmr";
		  sonic-ext:field-name "green_action";
      }
    }

    // COPP-GROUP STATE
    deviation /oc-copp:copp/oc-copp:copp-groups/oc-copp:copp-group/oc-copp:state/oc-copp:name {
      deviate add {
		  sonic-ext:field-transformer "copp_name_field_xfmr";
      }
    }

    deviation /oc-copp:copp/oc-copp:copp-groups/oc-copp:copp-group/oc-copp:state/oc-copp:trap-priority {
      deviate add {
		  sonic-ext:field-name "trap_priority";
      }
    }

    deviation /oc-copp:copp/oc-copp:copp-groups/oc-copp:copp-group/oc-copp:state/oc-copp:trap-action {
      deviate add {
		  sonic-ext:field-transformer "copp_trap_action_xfmr";
		  sonic-ext:field-name "trap_action";
      }
    }

    deviation /oc-copp:copp/oc-copp:copp-groups/oc-copp:copp-group/oc-copp:state/oc-copp:meter-type {
      deviate add {
		  sonic-ext:field-transformer "copp_meter_type_xfmr";
		  sonic-ext:field-name "meter_type";
      }
    }

    deviation /oc-copp:copp/oc-copp:copp-groups/oc-copp:copp-group/oc-copp:state/oc-copp:mode {
      deviate add {
		  sonic-ext:field-transformer "copp_mode_xfmr";
		  sonic-ext:field-name "mode";
      }
    }

    deviation /oc-copp:copp/oc-copp:copp-groups/oc-copp:copp-group/oc-copp:state/oc-copp:red-action {
      deviate add {
		  sonic-ext:field-transformer "copp_red_action_xfmr";
		  sonic-ext:field-name "red_action";
      }
    }

    deviation /oc-copp:copp/oc-copp:copp-groups/oc-copp:copp-group/oc-copp:state/oc-copp:yellow-action {
      deviate add {
		  sonic-ext:field-transformer "copp_yellow_action_xfmr";
		  sonic-ext:field-name "yellow_action";
      }
    }

    deviation /oc-copp:copp/oc-copp:copp-groups/oc-copp:copp-group/oc-copp:state/oc-copp:green-action {
      deviate add {
		  sonic-ext:field-transformer "copp_green_action_xfmr";
		  sonic-ext:field-name "green_action";
      }
    }

    deviation /oc-copp:copp/oc-copp:copp-traps/oc-copp:copp-trap {
      deviate add {
		  sonic-ext:table-name "COPP_TRAP";
      }
    }

    // COPP-TRAP CONFIG
    deviation /oc-copp:copp/oc-copp:copp-traps/oc-copp:copp-trap/oc-copp:config/oc-copp:name {
      deviate add {
		  sonic-ext:field-transformer "copp_name_field_xfmr";
      }
    }

    deviation /oc-copp:copp/oc-copp:copp-traps/oc-copp:copp-trap/oc-copp:config/oc-copp:trap-ids {
      deviate add {
		  sonic-ext:field-transformer "copp_trap_ids_xfmr";
		  sonic-ext:field-name "trap_ids";
      }
    }

    deviation /oc-copp:copp/oc-copp:copp-traps/oc-copp:copp-trap/oc-copp:config/oc-copp:trap-group {
      deviate add {
		  sonic-ext:field-transformer "copp_trap_group_xfmr";
		  sonic-ext:field-name "trap_group";
      }
    }

    // COPP-TRAP STATE
    deviation /oc-copp:copp/oc-copp:copp-traps/oc-copp:copp-trap/oc-copp:state/oc-copp:name {
      deviate add {
		  sonic-ext:field-transformer "copp_name_field_xfmr";
      }
    }

    deviation /oc-copp:copp/oc-copp:copp-traps/oc-copp:copp-trap/oc-copp:state/oc-copp:trap-ids {
      deviate add {
		  sonic-ext:field-transformer "copp_trap_ids_xfmr";
		  sonic-ext:field-name "trap_ids";
      }
    }

    deviation /oc-copp:copp/oc-copp:copp-traps/oc-copp:copp-trap/oc-copp:state/oc-copp:trap-group {
      deviate add {
		  sonic-ext:field-transformer "copp_trap_group_xfmr";
		  sonic-ext:field-name "trap_group";
      }
    }
}
