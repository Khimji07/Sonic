module openconfig-platform-diagnostics-annot {

    yang-version "1";
    namespace "http://openconfig.net/yang/platform-diagnostics-annot";
    prefix "oc-platform-diagnostics-annot";

    import openconfig-platform-diagnostics { prefix oc-pf-diag; }
    import sonic-extensions { prefix sonic-ext; }

    deviation /oc-pf-diag:cable-diagnostics {
      deviate add {
        sonic-ext:user-role-priv "write:netadmin";
      }
    }

    deviation /oc-pf-diag:cable-diagnostics/oc-pf-diag:cable-diagnostics-info {
      deviate add {
        sonic-ext:subtree-transformer "platform_diag_cd_xfmr";
      }
    }

    deviation /oc-pf-diag:transceiver-cmis {
      deviate add {
        sonic-ext:user-role-priv "write:netadmin";
      }
    }

    deviation /oc-pf-diag:transceiver-cmis/oc-pf-diag:transceiver-cmis-info {
      deviate add {
        sonic-ext:subtree-transformer "platform_diag_xcvr_cmis_xfmr";
      }
    }

    deviation /oc-pf-diag:transceiver-dom {
      deviate add {
        sonic-ext:user-role-priv "write:netadmin";
      }
    }

    deviation /oc-pf-diag:transceiver-dom/oc-pf-diag:transceiver-dom-info {
      deviate add {
        sonic-ext:db-name "STATE_DB";
        sonic-ext:subtree-transformer "platform_diag_xcvr_dom_xfmr";
      }
    }

    deviation /oc-pf-diag:transceiver-diagnostics {
      deviate add {
        sonic-ext:user-role-priv "write:netadmin";
      }
    }

    deviation /oc-pf-diag:transceiver-diagnostics/oc-pf-diag:transceiver-diagnostics-list {
      deviate add {
        sonic-ext:db-name "CONFIG_DB";
        sonic-ext:subtree-transformer "platform_diag_xcvr_diag_xfmr";
        sonic-ext:path-transformer "platform_diag_xcvr_diag_path_xfmr";
      }
    }
    deviation /oc-pf-diag:transceiver-diagnostics/oc-pf-diag:transceiver-diagnostics-list/oc-pf-diag:state {
      deviate add {
        sonic-ext:subscribe-on-change "disable";
      }
    }

}
