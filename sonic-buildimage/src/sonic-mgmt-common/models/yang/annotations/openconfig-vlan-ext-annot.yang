module openconfig-vlan-ext-annot {
    yang-version "1";

    namespace "http://openconfig.net/yang/annotation/openconfig-vlan-ext-annot";
    prefix "oc-vlan-ext-annot";

    import sonic-extensions { prefix sonic-ext; }
    import openconfig-vlan-ext { prefix oc-vlan-ext; }

    // meta
    organization
       "SONiC";

    contact
       "SONiC";

    description
       "SONIC vlan-ext";

    revision 2021-10-22 {
       description
          "Initial revision";
    }

    deviation /oc-vlan-ext:reserve-vlans/oc-vlan-ext:reserve-vlan/oc-vlan-ext:config   {
        deviate add {
        sonic-ext:table-name "RESERVED_VLAN";
      }
    }

    deviation /oc-vlan-ext:reserve-vlans  {
        deviate add {
        sonic-ext:user-role-priv "write:netadmin";
      }
    }

    deviation /oc-vlan-ext:reserve-vlans {
      deviate add {
        sonic-ext:db-name "STATE_DB";
        sonic-ext:table-name "RESERVED_VLAN";
        sonic-ext:key-transformer "reserved_vlan_key_xfmr";
        sonic-ext:subtree-transformer "reserved_vlan_subtree_xfmr";
      }
    }
}
