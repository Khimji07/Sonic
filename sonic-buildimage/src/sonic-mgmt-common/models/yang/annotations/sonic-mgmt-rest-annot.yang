module sonic-mgmt-rest-annot {
    namespace "http://github.com/Azure/sonic-mgmt-rest-annot";
    prefix "s-rest-annot";
    yang-version 1.1;

    import sonic-extensions { prefix sonic-ext; }
    import sonic-mgmt-rest { prefix smgmt-rest; }

    deviation /smgmt-rest:sonic-mgmt-rest {
        deviate add {
	    sonic-ext:user-role-priv "write:secadmin";
        }

    }
}
