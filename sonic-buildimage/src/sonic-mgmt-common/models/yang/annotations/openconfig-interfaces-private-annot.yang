module openconfig-interfaces-private-annot {

    yang-version "1";

    namespace "http://openconfig.net/yang/annotation/openconfig-interfaces-private-annot";
    prefix "oc-interfaces-priv-annot";

    import sonic-extensions { prefix sonic-ext; }
    import openconfig-interfaces { prefix oc-intf; }
    import openconfig-interfaces-private { prefix oc-intf-priv; }

    deviation /oc-intf-priv:clear-counters {
        deviate add {
            sonic-ext:rpc-callback "rpc_oc_clear_counters";
            sonic-ext:user-role-priv "rpc:netadmin";
        }
    }

    deviation /oc-intf-priv:vlan-replace {
        deviate add {
            sonic-ext:rpc-callback "rpc_oc_vlan_replace";
            sonic-ext:user-role-priv "rpc:netadmin";
        }
    }

    deviation /oc-intf-priv:get-neighbors {
        deviate add {
            sonic-ext:rpc-callback "rpc_get_neighbors";
            sonic-ext:user-role-priv "rpc:netadmin";
        }
    }

    deviation /oc-intf-priv:clear-interfaces-ip {
        deviate add {
            sonic-ext:rpc-callback "rpc_clear_interfaces_ip";
            sonic-ext:user-role-priv "rpc:netadmin";
        }
    }

    deviation /oc-intf-priv:default-interface-config {
        deviate add {
            sonic-ext:rpc-callback "rpc_default_port_config";
            sonic-ext:user-role-priv "rpc:netadmin";
        }
    }
}
