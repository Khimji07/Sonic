module openconfig-authmgr-annot {

    yang-version "1.1";

    namespace "http://openconfig.net/yang/annotation/oc-authmgr-annot";
    prefix "oc-authmgr-annot";

    import sonic-extensions { prefix sonic-ext; }
    import openconfig-authmgr { prefix oc-authmgr; }

    // meta
    organization
       "SONiC";

    contact
       "SONiC";

    description
       "SONIC PAC";

    revision "2021-04-23" {
    description
      "Initial public revision";
    reference "0.1.0";
    }

	deviation /oc-authmgr:authmgr {
                deviate add {
                        sonic-ext:user-role-priv "write:secadmin";
                }
        }

	deviation /oc-authmgr:authmgr/oc-authmgr:authmgr-global-config {
		deviate add {
			sonic-ext:subtree-transformer "authmgr_global_config_xfmr";
		}
    	}

        deviation /oc-authmgr:authmgr/oc-authmgr:authmgr-port-config/oc-authmgr:interface {
                deviate add {
			sonic-ext:table-name "PAC_PORT_CONFIG_TABLE";
                }
        }

	deviation /oc-authmgr:authmgr/oc-authmgr:authmgr-port-config/oc-authmgr:interface/oc-authmgr:config {
		deviate add {
			sonic-ext:subtree-transformer "authmgr_port_config_xfmr";
		}
	}

	deviation /oc-authmgr:authmgr/oc-authmgr:authmgr-port-config/oc-authmgr:interface/oc-authmgr:state {
		deviate add {
			sonic-ext:subtree-transformer "authmgr_port_config_xfmr";
		}
	}

        deviation /oc-authmgr:authmgr/oc-authmgr:authmgr-authenticated-clients-history {
                deviate add {
			sonic-ext:db-name "STATE_DB";
                }
        }

        deviation /oc-authmgr:authmgr/oc-authmgr:authmgr-authenticated-clients-history/oc-authmgr:entry {
                deviate add {
                        sonic-ext:table-name "PAC_CLIENT_HISTORY_TABLE";
			sonic-ext:key-transformer "authmgr_authctd_clients_history_key_xfmr";
        		sonic-ext:key-delim "|";
                }
        }

        deviation /oc-authmgr:authmgr/oc-authmgr:authmgr-authenticated-clients-history/oc-authmgr:entry/oc-authmgr:state/oc-authmgr:name {
                deviate add {
                        sonic-ext:field-transformer "authmgr_authctd_clients_history_entry_state_name_xfmr";
                }
        }

        deviation /oc-authmgr:authmgr/oc-authmgr:authmgr-authenticated-clients-history/oc-authmgr:entry/oc-authmgr:state/oc-authmgr:index {
                deviate add {
                        sonic-ext:field-transformer "authmgr_authctd_clients_history_entry_state_index_xfmr";
                 }
        }

        deviation /oc-authmgr:authmgr/oc-authmgr:authmgr-authenticated-clients-history/oc-authmgr:entry/oc-authmgr:state/oc-authmgr:client-mac-addr {
                deviate add {
	                sonic-ext:field-name "client_mac_addr";
                }
        }

        deviation /oc-authmgr:authmgr/oc-authmgr:authmgr-authenticated-clients-history/oc-authmgr:entry/oc-authmgr:state/oc-authmgr:authenticated-method {
                deviate add {
	                sonic-ext:field-name "authenticated_method";
          		sonic-ext:field-transformer "authmgr_authctd_clients_history_auth_method_fld_xfmr";
                }
        }

        deviation /oc-authmgr:authmgr/oc-authmgr:authmgr-authenticated-clients-history/oc-authmgr:entry/oc-authmgr:state/oc-authmgr:auth-status {
                deviate add {
	                sonic-ext:field-name "auth_status";
          		sonic-ext:field-transformer "authmgr_authctd_clients_history_auth_status_fld_xfmr";
                }
        }

        deviation /oc-authmgr:authmgr/oc-authmgr:authmgr-authenticated-clients {
                deviate add {
			sonic-ext:db-name "STATE_DB";
                }
        }

        deviation /oc-authmgr:authmgr/oc-authmgr:authmgr-authenticated-clients/oc-authmgr:authenticated-client {
                deviate add {
                        sonic-ext:table-name "PAC_AUTHENTICATED_CLIENT_OPER_TABLE";
			sonic-ext:key-transformer "authmgr_authctd_clients_key_xfmr";
        		sonic-ext:key-delim "|";
                }
        }

	deviation /oc-authmgr:authmgr/oc-authmgr:authmgr-authenticated-clients/oc-authmgr:authenticated-client/oc-authmgr:state/oc-authmgr:auth-status {
      		deviate add {
          		sonic-ext:field-transformer "authmgr_authctd_clients_auth_status_fld_xfmr";
          		sonic-ext:field-name "auth_status";
      		}
        }

	deviation /oc-authmgr:authmgr/oc-authmgr:authmgr-authenticated-clients/oc-authmgr:authenticated-client/oc-authmgr:state/oc-authmgr:authenticated-method {
                deviate add {
          		sonic-ext:field-transformer "authmgr_authctd_clients_auth_method_fld_xfmr";
                        sonic-ext:field-name "authenticated_method";
                }
        }

	deviation /oc-authmgr:authmgr/oc-authmgr:authmgr-authenticated-clients/oc-authmgr:authenticated-client/oc-authmgr:state/oc-authmgr:session-timeout-RADIUS {
                deviate add {
                        sonic-ext:field-name "session_timeout_RADIUS";
                }
        }

	deviation /oc-authmgr:authmgr/oc-authmgr:authmgr-authenticated-clients/oc-authmgr:authenticated-client/oc-authmgr:state/oc-authmgr:session-timeout-oper {
                deviate add {
                        sonic-ext:field-name "session_timeout_oper";
                }
        }

	deviation /oc-authmgr:authmgr/oc-authmgr:authmgr-authenticated-clients/oc-authmgr:authenticated-client/oc-authmgr:state/oc-authmgr:user-name {
                deviate add {
                        sonic-ext:field-name "user_name";
                }
        }

	deviation /oc-authmgr:authmgr/oc-authmgr:authmgr-authenticated-clients/oc-authmgr:authenticated-client/oc-authmgr:state/oc-authmgr:vlan-id {
                deviate add {
                        sonic-ext:field-name "vlan_id";
                }
        }

	deviation /oc-authmgr:authmgr/oc-authmgr:authmgr-authenticated-clients/oc-authmgr:authenticated-client/oc-authmgr:state/oc-authmgr:vlan-type {
                deviate add {
          		sonic-ext:field-transformer "authmgr_authctd_clients_vlan_type_fld_xfmr";
                        sonic-ext:field-name "vlan_type";
                }
        }

	deviation /oc-authmgr:authmgr/oc-authmgr:authmgr-authenticated-clients/oc-authmgr:authenticated-client/oc-authmgr:state/oc-authmgr:backend-auth-method {
                deviate add {
          		sonic-ext:field-transformer "authmgr_authctd_clients_backend_auth_method_fld_xfmr";
                        sonic-ext:field-name "backend_auth_method";
                }
        }

	deviation /oc-authmgr:authmgr/oc-authmgr:authmgr-authenticated-clients/oc-authmgr:authenticated-client/oc-authmgr:state/oc-authmgr:session-time {
                deviate add {
                        sonic-ext:field-transformer "authmgr_authctd_clients_session_time_fld_xfmr";
                        sonic-ext:field-name "session_time";
                }
        }

        deviation /oc-authmgr:authmgr/oc-authmgr:authmgr-authenticated-clients/oc-authmgr:authenticated-client/oc-authmgr:state/oc-authmgr:termination-action-time-left {
                deviate add {
                        sonic-ext:field-transformer "authmgr_authctd_clients_term_action_time_left_fld_xfmr";
                        sonic-ext:field-name "termination_action_time_left";
                }
        }

        deviation /oc-authmgr:authmgr/oc-authmgr:authmgr-authenticated-clients/oc-authmgr:authenticated-client/oc-authmgr:state/oc-authmgr:termination-action {
                deviate add {
                        sonic-ext:field-name "termination_action";
                }
        }

        deviation /oc-authmgr:authmgr/oc-authmgr:authmgr-authenticated-clients/oc-authmgr:authenticated-client/oc-authmgr:state/oc-authmgr:dacl-name {
                deviate add {
                        sonic-ext:field-name "dacl_name";
                }
        }

        deviation /oc-authmgr:authmgr/oc-authmgr:authmgr-authenticated-clients/oc-authmgr:authenticated-client/oc-authmgr:state/oc-authmgr:redirect-acl-name {
                deviate add {
                        sonic-ext:field-name "redirect_acl_name";
                }
        }

        deviation /oc-authmgr:authmgr/oc-authmgr:authmgr-authenticated-clients/oc-authmgr:authenticated-client/oc-authmgr:state/oc-authmgr:redirect-url {
                deviate add {
                        sonic-ext:field-name "redirect_url";
                }
        }

        deviation /oc-authmgr:authmgr/oc-authmgr:authmgr-authenticated-clients/oc-authmgr:authenticated-client/oc-authmgr:state/oc-authmgr:name {
                deviate add {
                        sonic-ext:field-transformer "authmgr_authctd_clients_state_name_xfmr";
                }
        }

        deviation /oc-authmgr:authmgr/oc-authmgr:authmgr-authenticated-clients/oc-authmgr:authenticated-client/oc-authmgr:state/oc-authmgr:macaddress {
                deviate add {
                        sonic-ext:field-transformer "authmgr_authctd_clients_state_macaddress_xfmr";
                }
        }

	deviation /oc-authmgr:authmgr/oc-authmgr:authmgr-port-operational-state-data {
                deviate add {
                        sonic-ext:db-name "STATE_DB";
                }
        }

        deviation /oc-authmgr:authmgr/oc-authmgr:authmgr-port-operational-state-data/oc-authmgr:ifname {
                deviate add {
                        sonic-ext:table-name "PAC_PORT_OPER_TABLE";
                        sonic-ext:key-delim "|";
                }
        }

        deviation /oc-authmgr:authmgr/oc-authmgr:authmgr-port-operational-state-data/oc-authmgr:ifname/oc-authmgr:state/oc-authmgr:name{
                deviate add {
                        sonic-ext:field-transformer "authmgr_port_oper_state_data_name_xfmr";
                }
        }

        deviation /oc-authmgr:authmgr/oc-authmgr:authmgr-port-operational-state-data/oc-authmgr:ifname/oc-authmgr:state/oc-authmgr:enabled-method-list {
                deviate add {
                        sonic-ext:field-name "enabled_method_list@";
          		sonic-ext:field-transformer "authmgr_port_oper_state_data_enabled_method_list_fld_xfmr";
                }
        }

	deviation /oc-authmgr:authmgr/oc-authmgr:authmgr-port-operational-state-data/oc-authmgr:ifname/oc-authmgr:state/oc-authmgr:enabled-priority-list {
                deviate add {
                        sonic-ext:field-name "enabled_priority_list@";
          		sonic-ext:field-transformer "authmgr_port_oper_state_data_enabled_priority_list_fld_xfmr";
                }
        }

        deviation /oc-authmgr:authmgr/oc-authmgr:authmgr-global-operational-state-data {
                deviate add {
                        sonic-ext:db-name "STATE_DB";
			sonic-ext:table-name "PAC_GLOBAL_OPER_TABLE";
			sonic-ext:key-transformer "authmgr_global_operational_state_data_key_xfmr";
                }
        }

        deviation /oc-authmgr:authmgr/oc-authmgr:authmgr-global-operational-state-data/oc-authmgr:state/oc-authmgr:num-clients-authenticated {
                deviate add {
                        sonic-ext:field-name "num_clients_authenticated";
                }
        }

        deviation /oc-authmgr:authmgr/oc-authmgr:authmgr-global-operational-state-data/oc-authmgr:state/oc-authmgr:num-clients-authenticated-monitor {
                deviate add {
                        sonic-ext:field-name "num_clients_authenticated_monitor";
		}
	}
}
