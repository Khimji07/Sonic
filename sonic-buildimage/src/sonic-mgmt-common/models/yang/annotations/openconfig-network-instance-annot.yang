module openconfig-network-instance-annot {

    yang-version "1.1";

    namespace "http://openconfig.net/yang/annotation/openconfig-network-instance-annot";
    prefix "oc-netinst-annot";

    import openconfig-network-instance { prefix oc-netinst; }
    import openconfig-network-instance-ext { prefix oc-netinst-ext; }
    import sonic-extensions { prefix sonic-ext; }
    import openconfig-network-instance-deviation { prefix oc-netinst-deviation; }
    import openconfig-bgp-ext { prefix oc-bgp-ext; }
    import openconfig-bgp-evpn-ext { prefix oc-bgp-evpn-ext; }
    import openconfig-bfd { prefix oc-bfd; }
    import openconfig-ospfv2-ext { prefix "oc-ospfv2-ext"; }
    import openconfig-igmp-ext { prefix "oc-igmp-ext"; }
    import openconfig-interfaces { prefix "oc-if"; }
    import openconfig-nexthop-tracking-ext { prefix "oc-nht-ext"; }

    import ietf-yang-types { prefix yang; }
    import openconfig-vxlan {prefix oc-vxlan; }
    import openconfig-mac-dampening { prefix oc-mac-damp; }

    // meta
    organization
       "SONiC";

    contact
       "SONiC";

    description
       "SONIC Network Instance Policy";

    revision 2022-10-12 {
       description
          "MAC aging time on-change support.";
    }

    revision 2022-07-20 {
       description
          "PIM on-change support.";
    }

    deviation /oc-netinst:network-instances {
      deviate add {
        sonic-ext:user-role-priv "write:netadmin";
      }
    }

    deviation /oc-netinst:network-instances {
      deviate add {
        sonic-ext:pre-transformer "network_instance_pre_xfmr";
        sonic-ext:post-transformer "network_instance_post_xfmr";
      }
    }

    deviation /oc-netinst:network-instances/oc-netinst:network-instance {
      deviate add {
        sonic-ext:table-transformer "network_instance_table_name_xfmr";
        sonic-ext:key-transformer "network_instance_table_key_xfmr";
      }
    }

    deviation /oc-netinst:network-instances/oc-netinst:network-instance/oc-netinst:config/oc-netinst:name {
      deviate add {
        sonic-ext:field-transformer "network_instance_name_field_xfmr";
      }
    }

    deviation /oc-netinst:network-instances/oc-netinst:network-instance/oc-netinst:config/oc-netinst:type {
      deviate add {
        sonic-ext:field-transformer "network_instance_type_field_xfmr";
      }
    }

    deviation /oc-netinst:network-instances/oc-netinst:network-instance/oc-netinst:config/oc-netinst:enabled {
      deviate add {
        sonic-ext:field-transformer "network_instance_enabled_field_xfmr";
      }
    }

    deviation /oc-netinst:network-instances/oc-netinst:network-instance/oc-netinst:config/oc-netinst:mtu {
      deviate add {
        sonic-ext:field-transformer "network_instance_mtu_field_xfmr";
      }
    }

    deviation /oc-netinst:network-instances/oc-netinst:network-instance/oc-netinst:config/oc-netinst:enabled-address-families {
      deviate add {
        sonic-ext:field-transformer "network_instance_enabled_addr_family_field_xfmr";
      }
    }

    deviation /oc-netinst:network-instances/oc-netinst:network-instance/oc-netinst:config/oc-netinst:router-id {
      deviate add {
        sonic-ext:field-transformer "network_instance_router_id_field_xfmr";
      }
    }

    deviation /oc-netinst:network-instances/oc-netinst:network-instance/oc-netinst:config/oc-netinst:route-distinguisher {
      deviate add {
        sonic-ext:field-transformer "network_instance_route_distinguisher_field_xfmr";
      }
    }

    deviation /oc-netinst:network-instances/oc-netinst:network-instance/oc-netinst:state/oc-netinst:name {
      deviate add {
        sonic-ext:field-transformer "network_instance_name_field_xfmr";
      }
    }

    deviation /oc-netinst:network-instances/oc-netinst:network-instance/oc-netinst:state/oc-netinst:type {
      deviate add {
        sonic-ext:field-transformer "network_instance_type_field_xfmr";
      }
    }

    deviation /oc-netinst:network-instances/oc-netinst:network-instance/oc-netinst:state/oc-netinst:enabled-address-families {
      deviate add {
        sonic-ext:field-transformer "network_instance_enabled_addr_fam_field_xfmr";
      }
    }

    deviation /oc-netinst:network-instances/oc-netinst:network-instance/oc-netinst:state/oc-netinst:mtu {
      deviate add {
        sonic-ext:field-transformer "network_instance_mtu_field_xfmr";
      }
    }

    deviation /oc-netinst:network-instances/oc-netinst:network-instance/oc-netinst:state/oc-netinst:enabled {
      deviate add {
        sonic-ext:field-transformer "network_instance_enabled_field_xfmr";
      }
    }

    deviation /oc-netinst:network-instances/oc-netinst:network-instance/oc-netinst:state/oc-netinst:router-id {
      deviate add {
        sonic-ext:field-transformer "network_instance_router_id_field_xfmr";
      }
    }

    deviation /oc-netinst:network-instances/oc-netinst:network-instance/oc-netinst:state/oc-netinst:route-distinguisher {
      deviate add {
        sonic-ext:field-transformer "network_instance_route_distinguisher_field_xfmr";
      }
    }

    deviation /oc-netinst:network-instances/oc-netinst:network-instance/oc-netinst:interfaces/oc-netinst:interface {
      deviate add {
        sonic-ext:subtree-transformer "network_instance_interface_binding_subtree_xfmr";
        sonic-ext:path-transformer "network_instance_interface_binding_path_xfmr";
      }
    }

    deviation /oc-netinst:network-instances/oc-netinst:network-instance/oc-netinst:interfaces/oc-netinst:interface/oc-netinst:state {
      deviate add {
        sonic-ext:subscribe-on-change "disable";
      }
    }

    deviation /oc-netinst:network-instances/oc-netinst:network-instance/oc-netinst:fdb/oc-netinst:mac-table {
      deviate add {
            sonic-ext:subtree-transformer "fdb_mac_table_xfmr";
      }
    }

    deviation /oc-netinst:network-instances/oc-netinst:network-instance/oc-netinst:fdb/oc-netinst:config/oc-netinst:mac-aging-time {
      deviate add {
            sonic-ext:subtree-transformer "mac_aging_time_xfmr";
            sonic-ext:path-transformer "mac_aging_time_path_xfmr";
      }
    }
    
    deviation /oc-netinst:network-instances/oc-netinst:network-instance/oc-netinst:fdb/oc-netinst:config {
      deviate add {
            sonic-ext:subtree-transformer "fdb_config_xfmr";
      }
    }

    deviation /oc-netinst:network-instances/oc-netinst:network-instance/oc-netinst:fdb/oc-netinst:config/oc-netinst:mac-learning {
      deviate add {
            sonic-ext:subscribe-on-change "disable";
      }
    }

    deviation /oc-netinst:network-instances/oc-netinst:network-instance/oc-netinst:fdb/oc-netinst:config/oc-netinst:maximum-entries {
      deviate add {
            sonic-ext:subscribe-on-change "disable";
      }
    }

    deviation /oc-netinst:network-instances/oc-netinst:network-instance/oc-netinst:fdb/oc-netinst:config/oc-netinst:static-count {
      deviate add {
            sonic-ext:subscribe-on-change "disable";
      }
    }

    deviation /oc-netinst:network-instances/oc-netinst:network-instance/oc-netinst:fdb/oc-netinst:config/oc-netinst:dynamic-count {
      deviate add {
            sonic-ext:subscribe-on-change "disable";
      }
    }

    deviation /oc-netinst:network-instances/oc-netinst:network-instance/oc-netinst:fdb/oc-netinst:state {
      deviate add {
            sonic-ext:subscribe-on-change "disable";
      }
    }

    deviation /oc-netinst:network-instances/oc-netinst:network-instance/oc-netinst:fdb/oc-netinst:state {
      deviate add {
            sonic-ext:subtree-transformer "fdb_state_get_xfmr";
      }
    }


    deviation /oc-netinst:network-instances/oc-netinst:network-instance/oc-mac-damp:mac-dampening {
        deviate add {
            sonic-ext:table-name "MAC_DAMPENING";
            sonic-ext:key-transformer "mac_dampening_config_key_xfmr";
        }
    }

    deviation /oc-netinst:network-instances/oc-netinst:network-instance/oc-mac-damp:mac-dampening/oc-mac-damp:config/oc-mac-damp:interval {
        deviate add {
            sonic-ext:field-transformer "mac_dampening_interval_fld_xfmr";
        }
    }

    deviation /oc-netinst:network-instances/oc-netinst:network-instance/oc-mac-damp:mac-dampening/oc-mac-damp:config/oc-mac-damp:threshold {
        deviate add {
            sonic-ext:field-transformer "mac_dampening_threshold_fld_xfmr";
        }
    }

    deviation /oc-netinst:network-instances/oc-netinst:network-instance/oc-mac-damp:mac-dampening/oc-mac-damp:state {
        deviate add {
            sonic-ext:table-name "MAC_DAMP_TABLE";
            sonic-ext:db-name "ASIC_DB";
            sonic-ext:subtree-transformer "mac_dampening_state_subtree_xfmr";
        }
    }

    deviation /oc-netinst:network-instances/oc-netinst:network-instance/oc-netinst-ext:rif-counters {
      deviate add {
        sonic-ext:table-name "SWITCH";
        sonic-ext:key-transformer "switch_key_xfmr";
      }
    }


    deviation /oc-netinst:network-instances/oc-netinst:network-instance/oc-netinst-ext:rif-counters/oc-netinst-ext:config/oc-netinst-ext:rif-counter-interval {
      deviate add {
            sonic-ext:subtree-transformer "rif_counter_interval_xfmr";
      }
    }

    deviation /oc-netinst:network-instances/oc-netinst:network-instance/oc-netinst:protocols {
        deviate add {
            sonic-ext:table-name "NONE";
        }
    }

    deviation /oc-netinst:network-instances/oc-netinst:network-instance/oc-netinst:protocols/oc-netinst:protocol {
        deviate add {
            sonic-ext:table-transformer "network_instance_protocols_ptotocol_table_name_xfmr";
            sonic-ext:key-transformer "network_instance_protocol_key_xfmr";
            sonic-ext:virtual-table "true";
        }
    }

    deviation /oc-netinst:network-instances/oc-netinst:network-instance/oc-netinst:protocols/oc-netinst:protocol/oc-netinst:bgp {
        deviate add {
            sonic-ext:table-transformer "bgp_gbl_tbl_xfmr";
            sonic-ext:key-transformer "bgp_gbl_tbl_key_xfmr";
        }
    }

    deviation /oc-netinst:network-instances/oc-netinst:network-instance/oc-netinst:protocols/oc-netinst:protocol/oc-netinst:bgp/oc-netinst:global {
        deviate add {
            sonic-ext:db-name "CONFIG_DB";
            sonic-ext:table-name "BGP_GLOBALS";
            sonic-ext:key-transformer "bgp_gbl_tbl_key_xfmr";
            sonic-ext:path-transformer "bgp_glb_path_Xfmr";
        }
    }

    deviation /oc-netinst:network-instances/oc-netinst:network-instance/oc-netinst:protocols/oc-netinst:protocol/oc-netinst:bgp/oc-netinst:global/oc-netinst:config/oc-netinst:router-id {
        deviate add {
            sonic-ext:field-name "router_id";
        }
    }

    deviation /oc-netinst:network-instances/oc-netinst:network-instance/oc-netinst:protocols/oc-netinst:protocol/oc-netinst:bgp/oc-netinst:global/oc-netinst:config/oc-netinst:as {
        deviate add {
            sonic-ext:field-transformer "bgp_local_asn_fld_xfmr";
            sonic-ext:field-name "local_asn";
        }
    }

    deviation /oc-netinst:network-instances/oc-netinst:network-instance/oc-netinst:protocols/oc-netinst:protocol/oc-netinst:bgp/oc-netinst:global/oc-netinst:config/oc-netinst:as-notation {
        deviate add {
            sonic-ext:field-transformer "bgp_as_notation_type_fld_xfmr";
            sonic-ext:field-name "as_notation";
        }
    }

    deviation /oc-netinst:network-instances/oc-netinst:network-instance/oc-netinst:protocols/oc-netinst:protocol/oc-netinst:bgp/oc-netinst:global/oc-netinst:state {
        deviate add {
            sonic-ext:subtree-transformer "bgp_gbl_state_xfmr";
            sonic-ext:subscribe-on-change "disable";
        }
    }

    deviation /oc-netinst:network-instances/oc-netinst:network-instance/oc-netinst:protocols/oc-netinst:protocol/oc-netinst:bgp/oc-netinst:global/oc-netinst:route-selection-options/oc-netinst:config/oc-netinst:always-compare-med {
      deviate add {
          sonic-ext:field-name "always_compare_med";
      }
    }

    deviation /oc-netinst:network-instances/oc-netinst:network-instance/oc-netinst:protocols/oc-netinst:protocol/oc-netinst:bgp/oc-netinst:global/oc-netinst:route-selection-options/oc-netinst:state/oc-netinst:always-compare-med {
      deviate add {
          sonic-ext:field-name "always_compare_med";
      }
    }

    deviation /oc-netinst:network-instances/oc-netinst:network-instance/oc-netinst:protocols/oc-netinst:protocol/oc-netinst:bgp/oc-netinst:global/oc-netinst:route-selection-options/oc-netinst:config/oc-netinst:ignore-as-path-length {
      deviate add {
          sonic-ext:field-name "ignore_as_path_length";
      }
    }

    deviation /oc-netinst:network-instances/oc-netinst:network-instance/oc-netinst:protocols/oc-netinst:protocol/oc-netinst:bgp/oc-netinst:global/oc-netinst:route-selection-options/oc-netinst:state/oc-netinst:ignore-as-path-length {
      deviate add {
          sonic-ext:field-name "ignore_as_path_length";
      }
    }

    deviation /oc-netinst:network-instances/oc-netinst:network-instance/oc-netinst:protocols/oc-netinst:protocol/oc-netinst:bgp/oc-netinst:global/oc-netinst:route-selection-options/oc-netinst:config/oc-netinst:external-compare-router-id {
      deviate add {
          sonic-ext:field-name "external_compare_router_id";
      }
    }

    deviation /oc-netinst:network-instances/oc-netinst:network-instance/oc-netinst:protocols/oc-netinst:protocol/oc-netinst:bgp/oc-netinst:global/oc-netinst:route-selection-options/oc-netinst:state/oc-netinst:external-compare-router-id {
      deviate add {
          sonic-ext:field-name "external_compare_router_id";
      }
    }

    deviation /oc-netinst:network-instances/oc-netinst:network-instance/oc-netinst:vlans {
      deviate add {
            sonic-ext:subtree-transformer "netinst_vlans_subtree_xfmr";
      }
    }

    deviation /oc-netinst:network-instances/oc-netinst:network-instance/oc-netinst:protocols/oc-netinst:protocol/oc-netinst:bgp/oc-netinst:global/oc-netinst:route-selection-options/oc-netinst:config/oc-netinst:med-confed {
      deviate add {
          sonic-ext:field-name "med_confed";
      }
    }

    deviation /oc-netinst:network-instances/oc-netinst:network-instance/oc-netinst:protocols/oc-netinst:protocol/oc-netinst:bgp/oc-netinst:global/oc-netinst:route-selection-options/oc-netinst:state/oc-netinst:med-confed {
      deviate add {
          sonic-ext:field-name "med_confed";
      }
    }

    deviation /oc-netinst:network-instances/oc-netinst:network-instance/oc-netinst:protocols/oc-netinst:protocol/oc-netinst:bgp/oc-netinst:global/oc-netinst:route-selection-options/oc-netinst:config/oc-netinst:med-missing-as-worst {
      deviate add {
          sonic-ext:field-name "med_missing_as_worst";
      }
    }

    deviation /oc-netinst:network-instances/oc-netinst:network-instance/oc-netinst:protocols/oc-netinst:protocol/oc-netinst:bgp/oc-netinst:global/oc-netinst:route-selection-options/oc-netinst:state/oc-netinst:med-missing-as-worst {
      deviate add {
          sonic-ext:field-name "med_missing_as_worst";
      }
    }

    deviation /oc-netinst:network-instances/oc-netinst:network-instance/oc-netinst:protocols/oc-netinst:protocol/oc-netinst:bgp/oc-netinst:global/oc-netinst:route-selection-options/oc-netinst:config/oc-netinst:compare-confed-as-path {
      deviate add {
          sonic-ext:field-name "compare_confed_as_path";
      }
    }

    deviation /oc-netinst:network-instances/oc-netinst:network-instance/oc-netinst:protocols/oc-netinst:protocol/oc-netinst:bgp/oc-netinst:global/oc-netinst:route-selection-options/oc-netinst:state/oc-netinst:compare-confed-as-path {
      deviate add {
          sonic-ext:field-name "compare_confed_as_path";
      }
    }

    deviation /oc-netinst:network-instances/oc-netinst:network-instance/oc-netinst:protocols/oc-netinst:protocol/oc-netinst:bgp/oc-netinst:global/oc-netinst:use-multiple-paths/oc-netinst:ebgp/oc-netinst:config/oc-netinst:allow-multiple-as {
      deviate add {
          sonic-ext:field-name "load_balance_mp_relax";
      }
    }

    deviation /oc-netinst:network-instances/oc-netinst:network-instance/oc-netinst:protocols/oc-netinst:protocol/oc-netinst:bgp/oc-netinst:global/oc-netinst:use-multiple-paths/oc-netinst:ebgp/oc-netinst:state/oc-netinst:allow-multiple-as {
      deviate add {
          sonic-ext:field-name "load_balance_mp_relax";
      }
    }

    deviation /oc-netinst:network-instances/oc-netinst:network-instance/oc-netinst:protocols/oc-netinst:protocol/oc-netinst:bgp/oc-netinst:global/oc-netinst:use-multiple-paths/oc-netinst:ebgp/oc-netinst:config/oc-netinst:as-set {
      deviate add {
        sonic-ext:field-name "as_path_mp_as_set";
      }
    }


    deviation /oc-netinst:network-instances/oc-netinst:network-instance/oc-netinst:protocols/oc-netinst:protocol/oc-netinst:bgp/oc-netinst:global/oc-netinst:use-multiple-paths/oc-netinst:ebgp/oc-netinst:state/oc-netinst:as-set {
      deviate add {
        sonic-ext:field-name "as_path_mp_as_set";
      }
    }

    deviation /oc-netinst:network-instances/oc-netinst:network-instance/oc-netinst:protocols/oc-netinst:protocol/oc-netinst:bgp/oc-netinst:global/oc-netinst:graceful-restart/oc-netinst:config/oc-netinst:enabled {
      deviate add {
          sonic-ext:field-name "graceful_restart_enable";
      }
    }

    deviation /oc-netinst:network-instances/oc-netinst:network-instance/oc-netinst:protocols/oc-netinst:protocol/oc-netinst:bgp/oc-netinst:global/oc-netinst:graceful-restart/oc-netinst:state/oc-netinst:enabled {
        deviate add {
          sonic-ext:field-name "graceful_restart_enable";
        }
    }


    deviation /oc-netinst:network-instances/oc-netinst:network-instance/oc-netinst:protocols/oc-netinst:protocol/oc-netinst:bgp/oc-netinst:global/oc-netinst:graceful-restart/oc-netinst:config/oc-netinst:restart-time {
      deviate add {
            sonic-ext:field-name "gr_restart_time";
      }
    }

    deviation /oc-netinst:network-instances/oc-netinst:network-instance/oc-netinst:protocols/oc-netinst:protocol/oc-netinst:bgp/oc-netinst:global/oc-netinst:graceful-restart/oc-netinst:state/oc-netinst:restart-time {
      deviate add {
            sonic-ext:field-name "gr_restart_time";
      }
    }

    deviation /oc-netinst:network-instances/oc-netinst:network-instance/oc-netinst:protocols/oc-netinst:protocol/oc-netinst:bgp/oc-netinst:global/oc-netinst:graceful-restart/oc-netinst:config/oc-netinst:stale-routes-time {
      deviate add {
            sonic-ext:field-name "gr_stale_routes_time";
      }
    }
    deviation /oc-netinst:network-instances/oc-netinst:network-instance/oc-netinst:protocols/oc-netinst:protocol/oc-netinst:bgp/oc-netinst:global/oc-netinst:graceful-restart/oc-netinst:state/oc-netinst:stale-routes-time {
      deviate add {
            sonic-ext:field-name "gr_stale_routes_time";
      }
    }

    deviation /oc-netinst:network-instances/oc-netinst:network-instance/oc-netinst:protocols/oc-netinst:protocol/oc-netinst:bgp/oc-netinst:global/oc-netinst:graceful-restart/oc-netinst:config/oc-netinst:preserve-fw-state {
      deviate add {
          sonic-ext:field-name "gr_preserve_fw_state";
      }
    }

    deviation /oc-netinst:network-instances/oc-netinst:network-instance/oc-netinst:protocols/oc-netinst:protocol/oc-netinst:bgp/oc-netinst:global/oc-netinst:graceful-restart/oc-netinst:state/oc-netinst:preserve-fw-state {
        deviate add {
          sonic-ext:field-name "gr_preserve_fw_state";
        }
    }

    deviation /oc-netinst:network-instances/oc-netinst:network-instance/oc-netinst:protocols/oc-netinst:protocol/oc-netinst:bgp/oc-netinst:global/oc-netinst:confederation/oc-netinst:config/oc-netinst:identifier {
      deviate add {
          sonic-ext:field-transformer "bgp_confed_id_fld_xfmr";
          sonic-ext:field-name "confed_id";
      }
    }

    deviation /oc-netinst:network-instances/oc-netinst:network-instance/oc-netinst:protocols/oc-netinst:protocol/oc-netinst:bgp/oc-netinst:global/oc-netinst:confederation/oc-netinst:config/oc-netinst:member-as {
      deviate add {
          sonic-ext:field-transformer "bgp_confed_peers_fld_xfmr";
          sonic-ext:field-name "confed_peers";
      }
    }

    deviation /oc-netinst:network-instances/oc-netinst:network-instance/oc-netinst:protocols/oc-netinst:protocol/oc-netinst:bgp/oc-netinst:global/oc-netinst:confederation/oc-netinst:state/oc-netinst:identifier {
      deviate add {
          sonic-ext:field-transformer "bgp_confed_id_fld_xfmr";
          sonic-ext:field-name "confed_id";
      }
    }

    deviation /oc-netinst:network-instances/oc-netinst:network-instance/oc-netinst:protocols/oc-netinst:protocol/oc-netinst:bgp/oc-netinst:global/oc-netinst:confederation/oc-netinst:state/oc-netinst:member-as {
      deviate add {
          sonic-ext:field-transformer "bgp_confed_peers_fld_xfmr";
          sonic-ext:field-name "confed_peers";
      }
    }

    deviation /oc-netinst:network-instances/oc-netinst:network-instance/oc-netinst:protocols/oc-netinst:protocol/oc-netinst:static-routes {
      deviate add {
          sonic-ext:subtree-transformer "static_routes_subtree_xfmr";
      }
    }

    deviation /oc-netinst:network-instances/oc-netinst:network-instance/oc-netinst:protocols/oc-netinst:protocol/oc-netinst:bgp/oc-netinst:neighbors {
      deviate add {
          sonic-ext:table-name "NONE";
      }
    }

    deviation /oc-netinst:network-instances/oc-netinst:network-instance/oc-netinst:protocols/oc-netinst:protocol/oc-netinst:bgp/oc-netinst:neighbors/oc-netinst:neighbor/oc-netinst:state {
        deviate add {
            sonic-ext:subtree-transformer "bgp_nbrs_nbr_state_xfmr";
            sonic-ext:subscribe-on-change "disable";
        }
    }

    deviation /oc-netinst:network-instances/oc-netinst:network-instance/oc-netinst:protocols/oc-netinst:protocol/oc-netinst:bgp/oc-netinst:neighbors/oc-netinst:neighbor/oc-netinst:auth-password {
        deviate add {
            sonic-ext:subtree-transformer "bgp_nbrs_nbr_auth_password_xfmr";
        }
    }

    deviation /oc-netinst:network-instances/oc-netinst:network-instance/oc-netinst:protocols/oc-netinst:protocol/oc-netinst:bgp/oc-netinst:peer-groups/oc-netinst:peer-group/oc-netinst:auth-password {
        deviate add {
            sonic-ext:subtree-transformer "bgp_pgrp_auth_password_xfmr";
        }
    }

    deviation /oc-netinst:network-instances/oc-netinst:network-instance/oc-netinst:protocols/oc-netinst:protocol/oc-netinst:bgp/oc-netinst:neighbors/oc-netinst:neighbor/oc-netinst:timers/oc-netinst:state {
        deviate add {
            sonic-ext:subtree-transformer "bgp_nbrs_nbr_state_xfmr";
            sonic-ext:subscribe-on-change "disable";
        }
    }

    deviation /oc-netinst:network-instances/oc-netinst:network-instance/oc-netinst:protocols/oc-netinst:protocol/oc-netinst:bgp/oc-netinst:neighbors/oc-netinst:neighbor/oc-netinst:transport/oc-netinst:state {
        deviate add {
            sonic-ext:subtree-transformer "bgp_nbrs_nbr_state_xfmr";
            sonic-ext:subscribe-on-change "disable";
        }
    }

    deviation /oc-netinst:network-instances/oc-netinst:network-instance/oc-netinst:protocols/oc-netinst:protocol/oc-netinst:bgp/oc-netinst:neighbors/oc-netinst:neighbor/oc-netinst:afi-safis/oc-netinst:afi-safi/oc-netinst:state {
        deviate add {
            sonic-ext:subtree-transformer "bgp_nbrs_nbr_af_state_xfmr";
            sonic-ext:subscribe-on-change "disable";
        }
    }

/* peer-groups->peer-group */
    deviation /oc-netinst:network-instances/oc-netinst:network-instance/oc-netinst:protocols/oc-netinst:protocol/oc-netinst:bgp/oc-netinst:peer-groups {
      deviate add {
            sonic-ext:table-name "NONE";
      }
    }

    deviation /oc-netinst:network-instances/oc-netinst:network-instance/oc-netinst:protocols/oc-netinst:protocol/oc-netinst:bgp/oc-netinst:peer-groups/oc-netinst:peer-group/oc-netinst:members-state {
      deviate add {
	sonic-ext:subtree-transformer "bgp_peer_group_mbrs_state_xfmr";
        sonic-ext:subscribe-on-change "disable";
      }
    }

    deviation /oc-netinst:network-instances/oc-netinst:network-instance/oc-netinst:protocols/oc-netinst:protocol/oc-netinst:bgp/oc-netinst:peer-groups {
      deviate add {
        sonic-ext:table-name "NONE";
      }
    }

/* peer-groups->peer-group */
    deviation /oc-netinst:network-instances/oc-netinst:network-instance/oc-netinst:protocols/oc-netinst:protocol/oc-netinst:bgp/oc-netinst:peer-groups/oc-netinst:peer-group {
      deviate add {
        sonic-ext:db-name "CONFIG_DB";
        sonic-ext:table-name "BGP_PEER_GROUP";
        sonic-ext:key-transformer "bgp_pgrp_tbl_key_xfmr";
        sonic-ext:path-transformer "bgp_peer_group_path_xfmr";
      }
    }

    deviation /oc-netinst:network-instances/oc-netinst:network-instance/oc-netinst:protocols/oc-netinst:protocol/oc-netinst:bgp/oc-netinst:peer-groups/oc-netinst:peer-group/oc-netinst:config/oc-netinst:peer-group-name {
      deviate add {
            sonic-ext:field-transformer "bgp_pgrp_name_fld_xfmr";
            sonic-ext:field-name "peer_group_name";
      }
    }

/* peer-group->ebgp-multihop */
    deviation /oc-netinst:network-instances/oc-netinst:network-instance/oc-netinst:protocols/oc-netinst:protocol/oc-netinst:bgp/oc-netinst:peer-groups/oc-netinst:peer-group/oc-netinst:ebgp-multihop/oc-netinst:config/oc-netinst:multihop-ttl {
      deviate add {
            sonic-ext:field-name "ebgp_multihop_ttl";
      }
    }

    deviation /oc-netinst:network-instances/oc-netinst:network-instance/oc-netinst:protocols/oc-netinst:protocol/oc-netinst:bgp/oc-netinst:peer-groups/oc-netinst:peer-group/oc-netinst:ebgp-multihop/oc-netinst:config/oc-netinst:enabled {
      deviate add {
            sonic-ext:field-name "ebgp_multihop";
      }
    }

    deviation /oc-netinst:network-instances/oc-netinst:network-instance/oc-netinst:protocols/oc-netinst:protocol/oc-netinst:bgp/oc-netinst:peer-groups/oc-netinst:peer-group/oc-netinst:ebgp-multihop/oc-netinst:state/oc-netinst:enabled {
      deviate add {
            sonic-ext:field-name "ebgp_multihop";
      }
    }

    deviation /oc-netinst:network-instances/oc-netinst:network-instance/oc-netinst:protocols/oc-netinst:protocol/oc-netinst:bgp/oc-netinst:peer-groups/oc-netinst:peer-group/oc-netinst:ebgp-multihop/oc-netinst:state/oc-netinst:multihop-ttl {
      deviate add {
            sonic-ext:field-name "ebgp_multihop_ttl";
      }
    }

/* peer-group->timers */
/* peer-group->timers->state */
/* peer-groups->timers->state->hold-time */
    deviation /oc-netinst:network-instances/oc-netinst:network-instance/oc-netinst:protocols/oc-netinst:protocol/oc-netinst:bgp/oc-netinst:peer-groups/oc-netinst:peer-group/oc-netinst:timers/oc-netinst:state/oc-netinst:hold-time {
      deviate add {
            sonic-ext:field-name "holdtime";
      }
    }

/* peer-groups->timers->state->keepalive-interval */
    deviation /oc-netinst:network-instances/oc-netinst:network-instance/oc-netinst:protocols/oc-netinst:protocol/oc-netinst:bgp/oc-netinst:peer-groups/oc-netinst:peer-group/oc-netinst:timers/oc-netinst:state/oc-netinst:keepalive-interval {
      deviate add {
            sonic-ext:field-name "keepalive";
      }
    }

/* peer-groups->timers->state->minimum-advertisement-interval */
    deviation /oc-netinst:network-instances/oc-netinst:network-instance/oc-netinst:protocols/oc-netinst:protocol/oc-netinst:bgp/oc-netinst:peer-groups/oc-netinst:peer-group/oc-netinst:timers/oc-netinst:state/oc-netinst:minimum-advertisement-interval {
	      deviate add {
		    sonic-ext:field-name "min_adv_interval";
      }
    }

/* peer-groups->timers->state->connect-retry */
    deviation /oc-netinst:network-instances/oc-netinst:network-instance/oc-netinst:protocols/oc-netinst:protocol/oc-netinst:bgp/oc-netinst:peer-groups/oc-netinst:peer-group/oc-netinst:timers/oc-netinst:state/oc-netinst:connect-retry {
      deviate add {
            sonic-ext:field-name "conn_retry";
      }
    }

/* peer-group->timers->config */
/* peer-group->timers->config->minimum-advertisement-interval */
    deviation /oc-netinst:network-instances/oc-netinst:network-instance/oc-netinst:protocols/oc-netinst:protocol/oc-netinst:bgp/oc-netinst:peer-groups/oc-netinst:peer-group/oc-netinst:timers/oc-netinst:config/oc-netinst:minimum-advertisement-interval {
      deviate add {
            sonic-ext:field-name "min_adv_interval";
      }
    }

/* peer-group->timers->config->connect-retry */
    deviation /oc-netinst:network-instances/oc-netinst:network-instance/oc-netinst:protocols/oc-netinst:protocol/oc-netinst:bgp/oc-netinst:peer-groups/oc-netinst:peer-group/oc-netinst:timers/oc-netinst:config/oc-netinst:connect-retry {
      deviate add {
            sonic-ext:field-name "conn_retry";
      }
    }

/* peer-group->timers->config->hold-time */
    deviation /oc-netinst:network-instances/oc-netinst:network-instance/oc-netinst:protocols/oc-netinst:protocol/oc-netinst:bgp/oc-netinst:peer-groups/oc-netinst:peer-group/oc-netinst:timers/oc-netinst:config/oc-netinst:hold-time {
      deviate add {
            sonic-ext:field-name "holdtime";
      }
    }

/* peer-group->timers->config->keepalive-interval */
    deviation /oc-netinst:network-instances/oc-netinst:network-instance/oc-netinst:protocols/oc-netinst:protocol/oc-netinst:bgp/oc-netinst:peer-groups/oc-netinst:peer-group/oc-netinst:timers/oc-netinst:config/oc-netinst:keepalive-interval {
      deviate add {
            sonic-ext:field-name "keepalive";
      }
    }

/* peer-group->config */
/* peer-group->config->description */
    deviation /oc-netinst:network-instances/oc-netinst:network-instance/oc-netinst:protocols/oc-netinst:protocol/oc-netinst:bgp/oc-netinst:peer-groups/oc-netinst:peer-group/oc-netinst:config/oc-netinst:description {
      deviate add {
            sonic-ext:field-name "name";
      }
    }

/* peer-group->config->peer-as */
    deviation /oc-netinst:network-instances/oc-netinst:network-instance/oc-netinst:protocols/oc-netinst:protocol/oc-netinst:bgp/oc-netinst:peer-groups/oc-netinst:peer-group/oc-netinst:config/oc-netinst:peer-as {
      deviate add {
            sonic-ext:field-transformer "bgp_pgrp_asn_fld_xfmr";
            sonic-ext:field-name "asn";
      }
    }

/* peer-group->config->peer-type */
    deviation /oc-netinst:network-instances/oc-netinst:network-instance/oc-netinst:protocols/oc-netinst:protocol/oc-netinst:bgp/oc-netinst:peer-groups/oc-netinst:peer-group/oc-netinst:config/oc-netinst:peer-type {
      deviate add {
            sonic-ext:field-transformer "bgp_pgrp_peer_type_fld_xfmr";
            sonic-ext:field-name "peer_type";
      }
    }

/* peer-group->config->local-as */
    deviation /oc-netinst:network-instances/oc-netinst:network-instance/oc-netinst:protocols/oc-netinst:protocol/oc-netinst:bgp/oc-netinst:peer-groups/oc-netinst:peer-group/oc-netinst:config/oc-netinst:local-as {
      deviate add {
            sonic-ext:field-transformer "bgp_pgrp_local_asn_fld_xfmr";
            sonic-ext:field-name "local_asn";
      }
    }

/* peer-group->state */
/* peer-group->state->peer-group-name */
    deviation /oc-netinst:network-instances/oc-netinst:network-instance/oc-netinst:protocols/oc-netinst:protocol/oc-netinst:bgp/oc-netinst:peer-groups/oc-netinst:peer-group/oc-netinst:state/oc-netinst:peer-group-name {
      deviate add {
            sonic-ext:field-transformer "bgp_pgrp_name_fld_xfmr";
            sonic-ext:field-name "peer_group_name";
      }
    }

/* peer-group->state->description */
    deviation /oc-netinst:network-instances/oc-netinst:network-instance/oc-netinst:protocols/oc-netinst:protocol/oc-netinst:bgp/oc-netinst:peer-groups/oc-netinst:peer-group/oc-netinst:state/oc-netinst:description {
      deviate add {
            sonic-ext:field-name "name";
      }
    }

/* peer-group->state->local-as */
    deviation /oc-netinst:network-instances/oc-netinst:network-instance/oc-netinst:protocols/oc-netinst:protocol/oc-netinst:bgp/oc-netinst:peer-groups/oc-netinst:peer-group/oc-netinst:state/oc-netinst:local-as {
      deviate add {
            sonic-ext:field-transformer "bgp_pgrp_local_asn_fld_xfmr";
            sonic-ext:field-name "local_asn";
      }
    }

/* peer-group->state->peer-as */
    deviation /oc-netinst:network-instances/oc-netinst:network-instance/oc-netinst:protocols/oc-netinst:protocol/oc-netinst:bgp/oc-netinst:peer-groups/oc-netinst:peer-group/oc-netinst:state/oc-netinst:peer-as {
      deviate add {
            sonic-ext:field-transformer "bgp_pgrp_asn_fld_xfmr";
            sonic-ext:field-name "asn";
      }
    }

/* peer-group->state->peer-type */
    deviation /oc-netinst:network-instances/oc-netinst:network-instance/oc-netinst:protocols/oc-netinst:protocol/oc-netinst:bgp/oc-netinst:peer-groups/oc-netinst:peer-group/oc-netinst:state/oc-netinst:peer-type {
      deviate add {
            sonic-ext:field-transformer "bgp_pgrp_peer_type_fld_xfmr";
            sonic-ext:field-name "peer_type";
      }
    }

/* peer-group->transport */
/* peer-group->transport->state */
/* peer-group->transport->state->passive-mode */
    deviation /oc-netinst:network-instances/oc-netinst:network-instance/oc-netinst:protocols/oc-netinst:protocol/oc-netinst:bgp/oc-netinst:peer-groups/oc-netinst:peer-group/oc-netinst:transport/oc-netinst:state/oc-netinst:passive-mode {
      deviate add {
            sonic-ext:field-name "passive_mode";
      }
    }

/* peer-group->transport->state->local-address */
    deviation /oc-netinst:network-instances/oc-netinst:network-instance/oc-netinst:protocols/oc-netinst:protocol/oc-netinst:bgp/oc-netinst:peer-groups/oc-netinst:peer-group/oc-netinst:transport/oc-netinst:state/oc-netinst:local-address {
      deviate add {
            sonic-ext:field-name "local_addr";
      }
    }

    deviation /oc-netinst:network-instances/oc-netinst:network-instance/oc-netinst:protocols/oc-netinst:protocol/oc-netinst:bgp/oc-netinst:peer-groups/oc-netinst:peer-group/oc-netinst:state/oc-netinst:enabled {
      deviate add {
            sonic-ext:field-name "admin_status";
      }
    }

/* peer-group->transport->config */
/* peer-group->transport->config->passive-mode */
    deviation /oc-netinst:network-instances/oc-netinst:network-instance/oc-netinst:protocols/oc-netinst:protocol/oc-netinst:bgp/oc-netinst:peer-groups/oc-netinst:peer-group/oc-netinst:transport/oc-netinst:config/oc-netinst:passive-mode {
      deviate add {
            sonic-ext:field-name "passive_mode";
      }
    }

/* peer-group->transport->config->local-address */
    deviation /oc-netinst:network-instances/oc-netinst:network-instance/oc-netinst:protocols/oc-netinst:protocol/oc-netinst:bgp/oc-netinst:peer-groups/oc-netinst:peer-group/oc-netinst:transport/oc-netinst:config/oc-netinst:local-address {
      deviate add {
            sonic-ext:field-name "local_addr";
      }
    }

    deviation /oc-netinst:network-instances/oc-netinst:network-instance/oc-netinst:protocols/oc-netinst:protocol/oc-netinst:bgp/oc-netinst:peer-groups/oc-netinst:peer-group/oc-netinst:config/oc-netinst:enabled {
      deviate add {
            sonic-ext:field-name "admin_status";
      }
    }

    deviation /oc-netinst:network-instances/oc-netinst:network-instance/oc-netinst:protocols/oc-netinst:protocol/oc-netinst:bgp/oc-netinst:peer-groups/oc-netinst:peer-group/oc-netinst:afi-safis {
      deviate add {
        sonic-ext:table-name "NONE";
      }
    }

/* peer-group->afi-safis->afi-safi */
    deviation /oc-netinst:network-instances/oc-netinst:network-instance/oc-netinst:protocols/oc-netinst:protocol/oc-netinst:bgp/oc-netinst:peer-groups/oc-netinst:peer-group/oc-netinst:afi-safis/oc-netinst:afi-safi {
      deviate add {
        sonic-ext:db-name "CONFIG_DB";
        sonic-ext:table-name "BGP_PEER_GROUP_AF";
        sonic-ext:key-transformer "bgp_af_pgrp_tbl_key_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn {
      deviate add {
        sonic-ext:get-validate "bgp_validate_pgrp_af";
        sonic-ext:subscribe-on-change "disable";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast {
      deviate add {
        sonic-ext:get-validate "bgp_validate_pgrp_af";
      }
    }
    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast {
      deviate add {
        sonic-ext:get-validate "bgp_validate_pgrp_af";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-netinst:enabled {
      deviate add {
            sonic-ext:field-name "admin_status";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-netinst:enabled {
      deviate add {
            sonic-ext:field-name "admin_status";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-netinst:afi-safi-name {
      deviate add {
            sonic-ext:field-transformer "bgp_pgrp_afi_safi_name_fld_xfmr";
            sonic-ext:field-name "afi_safi";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:config/oc-netinst:send-default-route {
      deviate add {
            sonic-ext:field-name "send_default_route";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:state/oc-netinst:send-default-route {
      deviate add {
            sonic-ext:field-name "send_default_route";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:state/oc-netinst:prevent-teardown {
      deviate add {
            sonic-ext:field-name "max_prefix_warning_only";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:state/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:state/oc-netinst:restart-timer {
      deviate add {
            sonic-ext:field-name "max_prefix_restart_interval";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:state/oc-netinst:max-prefixes {
      deviate add {
            sonic-ext:field-name "max_prefix_limit";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:config/oc-netinst:max-prefixes {
      deviate add {
            sonic-ext:field-name "max_prefix_limit";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:config/oc-netinst:prevent-teardown {
      deviate add {
            sonic-ext:field-name "max_prefix_warning_only";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:config/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:config/oc-netinst:restart-timer {
      deviate add {
            sonic-ext:field-name "max_prefix_restart_interval";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-netinst:afi-safi-name {
      deviate add {
            sonic-ext:field-transformer "bgp_pgrp_afi_safi_name_fld_xfmr";
            sonic-ext:field-name "afi_safi";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:state/oc-netinst:send-default-route {
      deviate add {
            sonic-ext:field-name "send_default_route";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:config/oc-netinst:restart-timer {
      deviate add {
            sonic-ext:field-name "max_prefix_restart_interval";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:config/oc-netinst:max-prefixes {
      deviate add {
            sonic-ext:field-name "max_prefix_limit";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:config/oc-netinst:prevent-teardown {
      deviate add {
            sonic-ext:field-name "max_prefix_warning_only";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:config/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:state/oc-netinst:restart-timer {
      deviate add {
            sonic-ext:field-name "max_prefix_restart_interval";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:state/oc-netinst:max-prefixes {
      deviate add {
            sonic-ext:field-name "max_prefix_limit";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:state/oc-netinst:prevent-teardown {
      deviate add {
            sonic-ext:field-name "max_prefix_warning_only";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:state/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:config/oc-netinst:send-default-route {
      deviate add {
            sonic-ext:field-name "send_default_route";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:state/oc-netinst:import-policy {
      deviate add {
            sonic-ext:field-name "route_map_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:state/oc-netinst:export-policy {
      deviate add {
            sonic-ext:field-name "route_map_out";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:config/oc-netinst:import-policy {
      deviate add {
            sonic-ext:field-name "route_map_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:config/oc-netinst:export-policy {
      deviate add {
            sonic-ext:field-name "route_map_out";
      }
    }

    deviation /oc-netinst:network-instances/oc-netinst:network-instance/oc-netinst:protocols/oc-netinst:protocol/oc-netinst:bgp/oc-netinst:global/oc-netinst:afi-safis {
      deviate add {
        sonic-ext:table-name "NONE";
      }
    }

    deviation /oc-netinst:network-instances/oc-netinst:network-instance/oc-netinst:protocols/oc-netinst:protocol/oc-netinst:bgp/oc-netinst:global/oc-netinst:afi-safis/oc-netinst:afi-safi {
      deviate add {
        sonic-ext:table-name "BGP_GLOBALS_AF";
        sonic-ext:key-transformer "bgp_gbl_afi_safi_key_xfmr";
      }
    }

    deviation /oc-netinst:network-instances/oc-netinst:network-instance/oc-netinst:protocols/oc-netinst:protocol/oc-netinst:bgp/oc-netinst:global/oc-netinst:afi-safis/oc-netinst:afi-safi/oc-netinst:l2vpn-evpn {
      deviate add {
        sonic-ext:get-validate "bgp_validate_gbl_af";
      }
    }

    deviation /oc-netinst:network-instances/oc-netinst:network-instance/oc-netinst:protocols/oc-netinst:protocol/oc-netinst:bgp/oc-netinst:global/oc-netinst:afi-safis/oc-netinst:afi-safi/oc-netinst:afi-safi-name {
      deviate add {
        sonic-ext:field-transformer "bgp_gbl_afi_safi_field_xfmr";
        sonic-ext:field-name "afi_safi";
      }
    }

    deviation /oc-netinst:network-instances/oc-netinst:network-instance/oc-netinst:protocols/oc-netinst:protocol/oc-netinst:bgp/oc-netinst:global/oc-netinst:afi-safis/oc-netinst:afi-safi/oc-netinst:config/oc-netinst:afi-safi-name {
      deviate add {
        sonic-ext:field-transformer "bgp_gbl_afi_safi_field_xfmr";
        sonic-ext:field-name "afi_safi";
      }
    }

    deviation /oc-netinst:network-instances/oc-netinst:network-instance/oc-netinst:protocols/oc-netinst:protocol/oc-netinst:bgp/oc-netinst:global/oc-netinst:afi-safis/oc-netinst:afi-safi/oc-netinst:state/oc-netinst:afi-safi-name {
      deviate add {
        sonic-ext:field-transformer "bgp_gbl_afi_safi_field_xfmr";
        sonic-ext:field-name "afi_safi";
      }
    }

    deviation /oc-netinst:network-instances/oc-netinst:network-instance/oc-netinst:protocols/oc-netinst:protocol/oc-netinst:bgp/oc-netinst:global/oc-netinst:afi-safis/oc-netinst:afi-safi/oc-netinst:use-multiple-paths/oc-netinst:ebgp/oc-netinst:config/oc-netinst:maximum-paths {
      deviate add {
        sonic-ext:field-name "max_ebgp_paths";
      }
    }

    deviation /oc-netinst:network-instances/oc-netinst:network-instance/oc-netinst:protocols/oc-netinst:protocol/oc-netinst:bgp/oc-netinst:global/oc-netinst:afi-safis/oc-netinst:afi-safi/oc-netinst:use-multiple-paths/oc-netinst:ibgp/oc-netinst:config/oc-netinst:maximum-paths {
      deviate add {
        sonic-ext:field-name "max_ibgp_paths";
      }
    }

    deviation /oc-netinst:network-instances/oc-netinst:network-instance/oc-netinst:protocols/oc-netinst:protocol/oc-netinst:bgp/oc-netinst:global/oc-netinst:afi-safis/oc-netinst:afi-safi/oc-netinst:use-multiple-paths/oc-netinst:ebgp/oc-netinst:state/oc-netinst:maximum-paths {
      deviate add {
        sonic-ext:field-name "max_ebgp_paths";
      }
    }

    deviation /oc-netinst:network-instances/oc-netinst:network-instance/oc-netinst:protocols/oc-netinst:protocol/oc-netinst:bgp/oc-netinst:global/oc-netinst:afi-safis/oc-netinst:afi-safi/oc-netinst:use-multiple-paths/oc-netinst:ibgp/oc-netinst:state/oc-netinst:maximum-paths {
      deviate add {
        sonic-ext:field-name "max_ibgp_paths";
      }
    }

    deviation /oc-netinst:network-instances/oc-netinst:network-instance/oc-netinst:protocols/oc-netinst:protocol/oc-netinst:bgp/oc-netinst:global/oc-netinst:afi-safis/oc-netinst:afi-safi/oc-netinst:use-multiple-paths/oc-netinst:ibgp/oc-netinst:config/oc-netinst:equal-cluster-length {
      deviate add {
        sonic-ext:field-name "ibgp_equal_cluster_length";
      }
    }

    deviation /oc-netinst:network-instances/oc-netinst:network-instance/oc-netinst:protocols/oc-netinst:protocol/oc-netinst:bgp/oc-netinst:global/oc-netinst:afi-safis/oc-netinst:afi-safi/oc-netinst:use-multiple-paths/oc-netinst:ibgp/oc-netinst:state/oc-netinst:equal-cluster-length {
      deviate add {
        sonic-ext:field-name "ibgp_equal_cluster_length";
      }
    }

    deviation /oc-netinst:network-instances/oc-netinst:network-instance/oc-netinst:table-connections {
      deviate add {
        sonic-ext:table-name "NONE";
        sonic-ext:get-validate "table_conns_validate_ni";
      }
    }

    deviation /oc-netinst:network-instances/oc-netinst:network-instance/oc-netinst:table-connections/oc-netinst:table-connection {
        deviate add {
            sonic-ext:table-name "ROUTE_REDISTRIBUTE";
            sonic-ext:key-transformer "route_table_conn_key_xfmr";
        }
    }

    deviation /oc-netinst:network-instances/oc-netinst:network-instance/oc-netinst:table-connections/oc-netinst:table-connection/oc-netinst:config/oc-netinst:src-protocol {
      deviate add {
        sonic-ext:field-transformer "route_table_src_protocol_xfmr";
      }
    }

    deviation /oc-netinst:network-instances/oc-netinst:network-instance/oc-netinst:table-connections/oc-netinst:table-connection/oc-netinst:config/oc-netinst:dst-protocol {
      deviate add {
        sonic-ext:field-transformer "route_table_dst_protocol_xfmr";
      }
    }

    deviation /oc-netinst:network-instances/oc-netinst:network-instance/oc-netinst:table-connections/oc-netinst:table-connection/oc-netinst:config/oc-netinst:metric {
      deviate add {
        sonic-ext:field-name "metric";
      }
    }

    deviation /oc-netinst:network-instances/oc-netinst:network-instance/oc-netinst:table-connections/oc-netinst:table-connection/oc-netinst:config/oc-netinst:address-family {
      deviate add {
        sonic-ext:field-transformer "route_table_addr_family_xfmr";
      }
    }

    deviation /oc-netinst:network-instances/oc-netinst:network-instance/oc-netinst:table-connections/oc-netinst:table-connection/oc-netinst:config/oc-netinst:import-policy {
      deviate add {
        sonic-ext:field-name "route_map";
      }
    }

    deviation /oc-netinst:network-instances/oc-netinst:network-instance/oc-netinst:table-connections/oc-netinst:table-connection/oc-netinst:state/oc-netinst:src-protocol {
      deviate add {
        sonic-ext:field-transformer "route_table_src_protocol_xfmr";
      }
    }

    deviation /oc-netinst:network-instances/oc-netinst:network-instance/oc-netinst:table-connections/oc-netinst:table-connection/oc-netinst:state/oc-netinst:dst-protocol {
      deviate add {
        sonic-ext:field-transformer "route_table_dst_protocol_xfmr";
      }
    }

    deviation /oc-netinst:network-instances/oc-netinst:network-instance/oc-netinst:table-connections/oc-netinst:table-connection/oc-netinst:state/oc-netinst:metric {
      deviate add {
        sonic-ext:field-name "metric";
      }
    }

    deviation /oc-netinst:network-instances/oc-netinst:network-instance/oc-netinst:table-connections/oc-netinst:table-connection/oc-netinst:state/oc-netinst:address-family {
      deviate add {
        sonic-ext:field-transformer "route_table_addr_family_xfmr";
      }
    }

    deviation /oc-netinst:network-instances/oc-netinst:network-instance/oc-netinst:table-connections/oc-netinst:table-connection/oc-netinst:state/oc-netinst:import-policy {
      deviate add {
        sonic-ext:field-name "route_map";
      }
    }

    deviation /oc-netinst:network-instances/oc-netinst:network-instance/oc-netinst:protocols/oc-netinst:protocol/oc-netinst:bgp/oc-netinst:global/oc-netinst:dynamic-neighbor-prefixes {
      deviate add {
        sonic-ext:table-name "NONE";
      }
    }

    deviation /oc-netinst:network-instances/oc-netinst:network-instance/oc-netinst:protocols/oc-netinst:protocol/oc-netinst:bgp/oc-netinst:global/oc-netinst:dynamic-neighbor-prefixes/oc-netinst:dynamic-neighbor-prefix {
      deviate add {
        sonic-ext:table-name "BGP_GLOBALS_LISTEN_PREFIX";
        sonic-ext:key-transformer "bgp_dyn_neigh_listen_key_xfmr";
      }
    }

    deviation /oc-netinst:network-instances/oc-netinst:network-instance/oc-netinst:protocols/oc-netinst:protocol/oc-netinst:bgp/oc-netinst:global/oc-netinst:dynamic-neighbor-prefixes/oc-netinst:dynamic-neighbor-prefix/oc-netinst:prefix {
      deviate add {
        sonic-ext:field-transformer "bgp_dyn_neigh_listen_field_xfmr";
        sonic-ext:field-name "ip_prefix";
      }
    }

    deviation /oc-netinst:network-instances/oc-netinst:network-instance/oc-netinst:protocols/oc-netinst:protocol/oc-netinst:bgp/oc-netinst:global/oc-netinst:dynamic-neighbor-prefixes/oc-netinst:dynamic-neighbor-prefix/oc-netinst:config/oc-netinst:prefix {
      deviate add {
        sonic-ext:field-transformer "bgp_dyn_neigh_listen_field_xfmr";
        sonic-ext:field-name "ip_prefix";
      }
    }

    deviation /oc-netinst:network-instances/oc-netinst:network-instance/oc-netinst:protocols/oc-netinst:protocol/oc-netinst:bgp/oc-netinst:global/oc-netinst:dynamic-neighbor-prefixes/oc-netinst:dynamic-neighbor-prefix/oc-netinst:state/oc-netinst:prefix {
      deviate add {
        sonic-ext:field-transformer "bgp_dyn_neigh_listen_field_xfmr";
        sonic-ext:field-name "ip_prefix";
      }
    }


    deviation /oc-netinst:network-instances/oc-netinst:network-instance/oc-netinst:protocols/oc-netinst:protocol/oc-netinst:bgp/oc-netinst:global/oc-netinst:dynamic-neighbor-prefixes/oc-netinst:dynamic-neighbor-prefix/oc-netinst:config/oc-netinst:peer-group {
      deviate add {
        sonic-ext:field-name "peer_group";
      }
    }

    deviation /oc-netinst:network-instances/oc-netinst:network-instance/oc-netinst:protocols/oc-netinst:protocol/oc-netinst:bgp/oc-netinst:global/oc-netinst:dynamic-neighbor-prefixes/oc-netinst:dynamic-neighbor-prefix/oc-netinst:state/oc-netinst:peer-group {
      deviate add {
        sonic-ext:field-name "peer_group";
      }
    }

    deviation /oc-netinst:network-instances/oc-netinst:network-instance/oc-netinst:protocols/oc-netinst:protocol/oc-netinst:bgp/oc-netinst:rib {
        deviate add {
            sonic-ext:table-name "NONE";
            sonic-ext:subtree-transformer "bgp_routes_get_xfmr";
            sonic-ext:subscribe-on-change "disable";
        }
    }

    deviation /oc-netinst:network-instances/oc-netinst:network-instance/oc-netinst:protocols/oc-netinst:protocol/oc-netinst:bgp/oc-netinst:global/oc-netinst:logging-options/oc-netinst:config/oc-netinst:log-neighbor-state-changes {
      deviate add {
            sonic-ext:field-name "log_nbr_state_changes";
      }
    }

    deviation /oc-netinst:network-instances/oc-netinst:network-instance/oc-netinst:protocols/oc-netinst:protocol/oc-netinst:bgp/oc-netinst:global/oc-netinst:logging-options/oc-netinst:state/oc-netinst:log-neighbor-state-changes {
      deviate add {
            sonic-ext:field-name "log_nbr_state_changes";
      }
    }

    deviation /oc-netinst:network-instances/oc-netinst:network-instance/oc-netinst:protocols/oc-netinst:protocol/oc-netinst:bgp/oc-netinst:global/oc-netinst:route-reflector/oc-netinst:config/oc-netinst:route-reflector-cluster-id {
      deviate add {
            sonic-ext:field-name "rr_cluster_id";
      }
    }

    deviation /oc-netinst:network-instances/oc-netinst:network-instance/oc-netinst:protocols/oc-netinst:protocol/oc-netinst:bgp/oc-netinst:global/oc-netinst:route-reflector/oc-netinst:config/oc-netinst:allow-outbound-policy {
      deviate add {
            sonic-ext:field-name "rr_allow_out_policy";
      }
    }

    deviation /oc-netinst:network-instances/oc-netinst:network-instance/oc-netinst:protocols/oc-netinst:protocol/oc-netinst:bgp/oc-netinst:global/oc-netinst:route-reflector/oc-netinst:state/oc-netinst:route-reflector-cluster-id {
      deviate add {
            sonic-ext:field-name "rr_cluster_id";
      }
    }

    deviation /oc-netinst:network-instances/oc-netinst:network-instance/oc-netinst:protocols/oc-netinst:protocol/oc-netinst:bgp/oc-netinst:global/oc-netinst:route-reflector/oc-netinst:state/oc-netinst:allow-outbound-policy {
      deviate add {
            sonic-ext:field-name "rr_allow_out_policy";
      }
    }

    deviation /oc-netinst:network-instances/oc-netinst:network-instance/oc-netinst:protocols/oc-netinst:protocol/oc-netinst:bgp/oc-netinst:global/oc-netinst:config/oc-netinst:disable-ebgp-connected-route-check {
      deviate add {
            sonic-ext:field-name "disable_ebgp_connected_rt_check";
      }
    }

    deviation /oc-netinst:network-instances/oc-netinst:network-instance/oc-netinst:protocols/oc-netinst:protocol/oc-netinst:bgp/oc-netinst:global/oc-netinst:config/oc-netinst:fast-external-failover {
      deviate add {
            sonic-ext:field-name "fast_external_failover";
      }
    }

    deviation /oc-netinst:network-instances/oc-netinst:network-instance/oc-netinst:protocols/oc-netinst:protocol/oc-netinst:bgp/oc-netinst:global/oc-netinst:config/oc-netinst:network-import-check {
      deviate add {
            sonic-ext:field-name "network_import_check";
      }
    }

    deviation /oc-netinst:network-instances/oc-netinst:network-instance/oc-netinst:protocols/oc-netinst:protocol/oc-netinst:bgp/oc-netinst:global/oc-netinst:config/oc-netinst:graceful-shutdown {
      deviate add {
            sonic-ext:field-name "graceful_shutdown";
      }
    }

    deviation /oc-netinst:network-instances/oc-netinst:network-instance/oc-netinst:protocols/oc-netinst:protocol/oc-netinst:bgp/oc-netinst:global/oc-netinst:config/oc-netinst:clnt-to-clnt-reflection {
      deviate add {
            sonic-ext:field-name "rr_clnt_to_clnt_reflection";
      }
    }


    deviation /oc-netinst:network-instances/oc-netinst:network-instance/oc-netinst:protocols/oc-netinst:protocol/oc-netinst:bgp/oc-netinst:global/oc-netinst:config/oc-netinst:max-dynamic-neighbors {
      deviate add {
            sonic-ext:field-name "max_dynamic_neighbors";
      }
    }

    deviation /oc-netinst:network-instances/oc-netinst:network-instance/oc-netinst:protocols/oc-netinst:protocol/oc-netinst:bgp/oc-netinst:global/oc-netinst:config/oc-netinst:read-quanta {
      deviate add {
            sonic-ext:field-name "read_quanta";
      }
    }

    deviation /oc-netinst:network-instances/oc-netinst:network-instance/oc-netinst:protocols/oc-netinst:protocol/oc-netinst:bgp/oc-netinst:global/oc-netinst:config/oc-netinst:write-quanta {
      deviate add {
            sonic-ext:field-name "write_quanta";
      }
    }

    deviation /oc-netinst:network-instances/oc-netinst:network-instance/oc-netinst:protocols/oc-netinst:protocol/oc-netinst:bgp/oc-netinst:global/oc-netinst:config/oc-netinst:coalesce-time {
      deviate add {
            sonic-ext:field-name "coalesce_time";
      }
    }

    deviation /oc-netinst:network-instances/oc-netinst:network-instance/oc-netinst:protocols/oc-netinst:protocol/oc-netinst:bgp/oc-netinst:global/oc-netinst:config/oc-netinst:route-map-process-delay {
      deviate add {
            sonic-ext:field-name "route_map_process_delay";
      }
    }

    deviation /oc-netinst:network-instances/oc-netinst:network-instance/oc-netinst:protocols/oc-netinst:protocol/oc-netinst:bgp/oc-netinst:global/oc-netinst:config/oc-netinst:deterministic-med {
      deviate add {
            sonic-ext:field-name "deterministic_med";
      }
    }

    deviation /oc-netinst:network-instances/oc-netinst:network-instance/oc-netinst:protocols/oc-netinst:protocol/oc-netinst:bgp/oc-netinst:global/oc-netinst:config/oc-netinst:ebgp-requires-policy {
      deviate add {
            sonic-ext:field-name "ebgp_requires_policy";
      }
    }


    deviation /oc-netinst:network-instances/oc-netinst:network-instance/oc-netinst:protocols/oc-netinst:protocol/oc-netinst:bgp/oc-netinst:global/oc-netinst:state/oc-netinst:disable-ebgp-connected-route-check {
      deviate add {
            sonic-ext:field-name "disable_ebgp_connected_rt_check";
      }
    }

    deviation /oc-netinst:network-instances/oc-netinst:network-instance/oc-netinst:protocols/oc-netinst:protocol/oc-netinst:bgp/oc-netinst:global/oc-netinst:state/oc-netinst:fast-external-failover {
      deviate add {
            sonic-ext:field-name "fast_external_failover";
      }
    }

    deviation /oc-netinst:network-instances/oc-netinst:network-instance/oc-netinst:protocols/oc-netinst:protocol/oc-netinst:bgp/oc-netinst:global/oc-netinst:state/oc-netinst:network-import-check {
      deviate add {
            sonic-ext:field-name "network_import_check";
      }
    }

    deviation /oc-netinst:network-instances/oc-netinst:network-instance/oc-netinst:protocols/oc-netinst:protocol/oc-netinst:bgp/oc-netinst:global/oc-netinst:state/oc-netinst:graceful-shutdown {
      deviate add {
            sonic-ext:field-name "graceful_shutdown";
      }
    }

    deviation /oc-netinst:network-instances/oc-netinst:network-instance/oc-netinst:protocols/oc-netinst:protocol/oc-netinst:bgp/oc-netinst:global/oc-netinst:state/oc-netinst:clnt-to-clnt-reflection {
      deviate add {
            sonic-ext:field-name "rr_clnt_to_clnt_reflection";
      }
    }


    deviation /oc-netinst:network-instances/oc-netinst:network-instance/oc-netinst:protocols/oc-netinst:protocol/oc-netinst:bgp/oc-netinst:global/oc-netinst:state/oc-netinst:max-dynamic-neighbors {
      deviate add {
            sonic-ext:field-name "max_dynamic_neighbors";
      }
    }

    deviation /oc-netinst:network-instances/oc-netinst:network-instance/oc-netinst:protocols/oc-netinst:protocol/oc-netinst:bgp/oc-netinst:global/oc-netinst:state/oc-netinst:read-quanta {
      deviate add {
            sonic-ext:field-name "read_quanta";
      }
    }

    deviation /oc-netinst:network-instances/oc-netinst:network-instance/oc-netinst:protocols/oc-netinst:protocol/oc-netinst:bgp/oc-netinst:global/oc-netinst:state/oc-netinst:write-quanta {
      deviate add {
            sonic-ext:field-name "write_quanta";
      }
    }

    deviation /oc-netinst:network-instances/oc-netinst:network-instance/oc-netinst:protocols/oc-netinst:protocol/oc-netinst:bgp/oc-netinst:global/oc-netinst:state/oc-netinst:coalesce-time {
      deviate add {
            sonic-ext:field-name "coalesce_time";
      }
    }

    deviation /oc-netinst:network-instances/oc-netinst:network-instance/oc-netinst:protocols/oc-netinst:protocol/oc-netinst:bgp/oc-netinst:global/oc-netinst:state/oc-netinst:route-map-process-delay {
      deviate add {
            sonic-ext:field-name "route_map_process_delay";
      }
    }

    deviation /oc-netinst:network-instances/oc-netinst:network-instance/oc-netinst:protocols/oc-netinst:protocol/oc-netinst:bgp/oc-netinst:global/oc-netinst:state/oc-netinst:deterministic-med {
      deviate add {
            sonic-ext:field-name "deterministic_med";
      }
    }

    deviation /oc-netinst:network-instances/oc-netinst:network-instance/oc-netinst:protocols/oc-netinst:protocol/oc-netinst:bgp/oc-netinst:global/oc-netinst:state/oc-netinst:ebgp-requires-policy {
      deviate add {
            sonic-ext:field-name "ebgp_requires_policy";
      }
    }

    deviation /oc-netinst:network-instances/oc-netinst:network-instance/oc-netinst:protocols/oc-netinst:protocol/oc-netinst:bgp/oc-netinst:global/oc-netinst:afi-safis/oc-netinst:afi-safi/oc-netinst:route-flap-damping/oc-netinst:config/oc-netinst:enabled {
      deviate add {
            sonic-ext:field-name "route_flap_dampen";
      }
    }

    deviation /oc-netinst:network-instances/oc-netinst:network-instance/oc-netinst:protocols/oc-netinst:protocol/oc-netinst:bgp/oc-netinst:global/oc-netinst:afi-safis/oc-netinst:afi-safi/oc-netinst:route-flap-damping/oc-netinst:config/oc-netinst:half-life {
      deviate add {
            sonic-ext:field-name "route_flap_dampen_half_life";
      }
    }

    deviation /oc-netinst:network-instances/oc-netinst:network-instance/oc-netinst:protocols/oc-netinst:protocol/oc-netinst:bgp/oc-netinst:global/oc-netinst:afi-safis/oc-netinst:afi-safi/oc-netinst:route-flap-damping/oc-netinst:config/oc-netinst:reuse-threshold {
      deviate add {
            sonic-ext:field-name "route_flap_dampen_reuse_threshold";
      }
    }

    deviation /oc-netinst:network-instances/oc-netinst:network-instance/oc-netinst:protocols/oc-netinst:protocol/oc-netinst:bgp/oc-netinst:global/oc-netinst:afi-safis/oc-netinst:afi-safi/oc-netinst:route-flap-damping/oc-netinst:config/oc-netinst:suppress-threshold {
      deviate add {
            sonic-ext:field-name "route_flap_dampen_suppress_threshold";
      }
    }

    deviation /oc-netinst:network-instances/oc-netinst:network-instance/oc-netinst:protocols/oc-netinst:protocol/oc-netinst:bgp/oc-netinst:global/oc-netinst:afi-safis/oc-netinst:afi-safi/oc-netinst:route-flap-damping/oc-netinst:config/oc-netinst:max-suppress {
      deviate add {
            sonic-ext:field-name "route_flap_dampen_max_suppress";
      }
    }


    deviation /oc-netinst:network-instances/oc-netinst:network-instance/oc-netinst:protocols/oc-netinst:protocol/oc-netinst:bgp/oc-netinst:global/oc-netinst:afi-safis/oc-netinst:afi-safi/oc-netinst:route-flap-damping/oc-netinst:state/oc-netinst:enabled {
      deviate add {
            sonic-ext:field-name "route_flap_dampen";
      }
    }

    deviation /oc-netinst:network-instances/oc-netinst:network-instance/oc-netinst:protocols/oc-netinst:protocol/oc-netinst:bgp/oc-netinst:global/oc-netinst:afi-safis/oc-netinst:afi-safi/oc-netinst:route-flap-damping/oc-netinst:state/oc-netinst:half-life {
      deviate add {
            sonic-ext:field-name "route_flap_dampen_half_life";
      }
    }

    deviation /oc-netinst:network-instances/oc-netinst:network-instance/oc-netinst:protocols/oc-netinst:protocol/oc-netinst:bgp/oc-netinst:global/oc-netinst:afi-safis/oc-netinst:afi-safi/oc-netinst:route-flap-damping/oc-netinst:state/oc-netinst:reuse-threshold {
      deviate add {
            sonic-ext:field-name "route_flap_dampen_reuse_threshold";
      }
    }

    deviation /oc-netinst:network-instances/oc-netinst:network-instance/oc-netinst:protocols/oc-netinst:protocol/oc-netinst:bgp/oc-netinst:global/oc-netinst:afi-safis/oc-netinst:afi-safi/oc-netinst:route-flap-damping/oc-netinst:state/oc-netinst:suppress-threshold {
      deviate add {
            sonic-ext:field-name "route_flap_dampen_suppress_threshold";
      }
    }

    deviation /oc-netinst:network-instances/oc-netinst:network-instance/oc-netinst:protocols/oc-netinst:protocol/oc-netinst:bgp/oc-netinst:global/oc-netinst:afi-safis/oc-netinst:afi-safi/oc-netinst:route-flap-damping/oc-netinst:state/oc-netinst:max-suppress {
      deviate add {
            sonic-ext:field-name "route_flap_dampen_max_suppress";
      }
    }

    deviation /oc-netinst:network-instances/oc-netinst:network-instance/oc-netinst:protocols/oc-netinst:protocol/oc-netinst:bgp/oc-netinst:global/oc-netinst:global-defaults/oc-netinst:config/oc-netinst:ipv4-unicast {
      deviate add {
            sonic-ext:field-name "default_ipv4_unicast";
      }
    }


    deviation /oc-netinst:network-instances/oc-netinst:network-instance/oc-netinst:protocols/oc-netinst:protocol/oc-netinst:bgp/oc-netinst:global/oc-netinst:global-defaults/oc-netinst:config/oc-netinst:local-preference {
      deviate add {
            sonic-ext:field-name "default_local_preference";
      }
    }

    deviation /oc-netinst:network-instances/oc-netinst:network-instance/oc-netinst:protocols/oc-netinst:protocol/oc-netinst:bgp/oc-netinst:global/oc-netinst:global-defaults/oc-netinst:config/oc-netinst:show-hostname {
      deviate add {
            sonic-ext:field-name "default_show_hostname";
      }
    }

    deviation /oc-netinst:network-instances/oc-netinst:network-instance/oc-netinst:protocols/oc-netinst:protocol/oc-netinst:bgp/oc-netinst:global/oc-netinst:global-defaults/oc-netinst:config/oc-netinst:shutdown {
      deviate add {
            sonic-ext:field-name "default_shutdown";
      }
    }

    deviation /oc-netinst:network-instances/oc-netinst:network-instance/oc-netinst:protocols/oc-netinst:protocol/oc-netinst:bgp/oc-netinst:global/oc-netinst:global-defaults/oc-netinst:config/oc-netinst:subgroup-pkt-queue-max {
      deviate add {
            sonic-ext:field-name "default_subgroup_pkt_queue_max";
      }
    }

    deviation /oc-netinst:network-instances/oc-netinst:network-instance/oc-netinst:protocols/oc-netinst:protocol/oc-netinst:bgp/oc-netinst:global/oc-netinst:global-defaults/oc-netinst:state/oc-netinst:ipv4-unicast {
      deviate add {
            sonic-ext:field-name "default_ipv4_unicast";
      }
    }

    deviation /oc-netinst:network-instances/oc-netinst:network-instance/oc-netinst:protocols/oc-netinst:protocol/oc-netinst:bgp/oc-netinst:global/oc-netinst:global-defaults/oc-netinst:state/oc-netinst:local-preference {
      deviate add {
            sonic-ext:field-name "default_local_preference";
      }
    }

    deviation /oc-netinst:network-instances/oc-netinst:network-instance/oc-netinst:protocols/oc-netinst:protocol/oc-netinst:bgp/oc-netinst:global/oc-netinst:global-defaults/oc-netinst:state/oc-netinst:show-hostname {
      deviate add {
            sonic-ext:field-name "default_show_hostname";
      }
    }

    deviation /oc-netinst:network-instances/oc-netinst:network-instance/oc-netinst:protocols/oc-netinst:protocol/oc-netinst:bgp/oc-netinst:global/oc-netinst:global-defaults/oc-netinst:state/oc-netinst:shutdown {
      deviate add {
            sonic-ext:field-name "default_shutdown";
      }
    }

    deviation /oc-netinst:network-instances/oc-netinst:network-instance/oc-netinst:protocols/oc-netinst:protocol/oc-netinst:bgp/oc-netinst:global/oc-netinst:global-defaults/oc-netinst:state/oc-netinst:subgroup-pkt-queue-max {
      deviate add {
            sonic-ext:field-name "default_subgroup_pkt_queue_max";
      }
    }

    deviation /oc-netinst:network-instances/oc-netinst:network-instance/oc-netinst:protocols/oc-netinst:protocol/oc-netinst:bgp/oc-netinst:global/oc-netinst:update-delay/oc-netinst:config/oc-netinst:max-delay {
      deviate add {
            sonic-ext:field-name "max_delay";
      }
    }

    deviation /oc-netinst:network-instances/oc-netinst:network-instance/oc-netinst:protocols/oc-netinst:protocol/oc-netinst:bgp/oc-netinst:global/oc-netinst:update-delay/oc-netinst:config/oc-netinst:establish-wait {
      deviate add {
            sonic-ext:field-name "establish_wait";
      }
    }

    deviation /oc-netinst:network-instances/oc-netinst:network-instance/oc-netinst:protocols/oc-netinst:protocol/oc-netinst:bgp/oc-netinst:global/oc-netinst:update-delay/oc-netinst:state/oc-netinst:max-delay {
      deviate add {
            sonic-ext:field-name "max_delay";
      }
    }

    deviation /oc-netinst:network-instances/oc-netinst:network-instance/oc-netinst:protocols/oc-netinst:protocol/oc-netinst:bgp/oc-netinst:global/oc-netinst:update-delay/oc-netinst:state/oc-netinst:establish-wait {
      deviate add {
            sonic-ext:field-name "establish_wait";
      }
    }

    deviation /oc-netinst:network-instances/oc-netinst:network-instance/oc-netinst:protocols/oc-netinst:protocol/oc-netinst:bgp/oc-netinst:global/oc-netinst:max-med/oc-netinst:config/oc-netinst:time {
      deviate add {
            sonic-ext:field-name "max_med_time";
      }
    }

    deviation /oc-netinst:network-instances/oc-netinst:network-instance/oc-netinst:protocols/oc-netinst:protocol/oc-netinst:bgp/oc-netinst:global/oc-netinst:max-med/oc-netinst:config/oc-netinst:max-med-val {
      deviate add {
            sonic-ext:field-name "max_med_val";
      }
    }

    deviation /oc-netinst:network-instances/oc-netinst:network-instance/oc-netinst:protocols/oc-netinst:protocol/oc-netinst:bgp/oc-netinst:global/oc-netinst:max-med/oc-netinst:config/oc-netinst:administrative {
      deviate add {
            sonic-ext:field-name "max_med_admin";
      }
    }

    deviation /oc-netinst:network-instances/oc-netinst:network-instance/oc-netinst:protocols/oc-netinst:protocol/oc-netinst:bgp/oc-netinst:global/oc-netinst:max-med/oc-netinst:config/oc-netinst:admin-max-med-val {
      deviate add {
            sonic-ext:field-name "max_med_admin_val";
      }
    }


    deviation /oc-netinst:network-instances/oc-netinst:network-instance/oc-netinst:protocols/oc-netinst:protocol/oc-netinst:bgp/oc-netinst:global/oc-netinst:max-med/oc-netinst:state/oc-netinst:administrative {
      deviate add {
            sonic-ext:field-name "max_med_admin";
      }
    }

    deviation /oc-netinst:network-instances/oc-netinst:network-instance/oc-netinst:protocols/oc-netinst:protocol/oc-netinst:bgp/oc-netinst:global/oc-netinst:max-med/oc-netinst:state/oc-netinst:admin-max-med-val {
      deviate add {
            sonic-ext:field-name "max_med_admin_val";
      }
    }

    deviation /oc-netinst:network-instances/oc-netinst:network-instance/oc-netinst:protocols/oc-netinst:protocol/oc-netinst:bgp/oc-netinst:global/oc-netinst:max-med/oc-netinst:state/oc-netinst:time {
      deviate add {
            sonic-ext:field-name "max_med_time";
      }
    }

    deviation /oc-netinst:network-instances/oc-netinst:network-instance/oc-netinst:protocols/oc-netinst:protocol/oc-netinst:bgp/oc-netinst:global/oc-netinst:max-med/oc-netinst:state/oc-netinst:max-med-val {
      deviate add {
            sonic-ext:field-name "max_med_val";
      }
    }

    deviation /oc-netinst:network-instances/oc-netinst:network-instance/oc-netinst:protocols/oc-netinst:protocol/oc-netinst:bgp/oc-netinst:global/oc-netinst:config/oc-netinst:hold-time {
      deviate add {
            sonic-ext:field-name "holdtime";
      }
    }

    deviation /oc-netinst:network-instances/oc-netinst:network-instance/oc-netinst:protocols/oc-netinst:protocol/oc-netinst:bgp/oc-netinst:global/oc-netinst:config/oc-netinst:keepalive-interval {
      deviate add {
            sonic-ext:field-name "keepalive";
      }
    }

    deviation /oc-netinst:network-instances/oc-netinst:network-instance/oc-netinst:protocols/oc-netinst:protocol/oc-netinst:bgp/oc-netinst:global/oc-netinst:state/oc-netinst:hold-time {
      deviate add {
            sonic-ext:field-name "holdtime";
      }
    }

    deviation /oc-netinst:network-instances/oc-netinst:network-instance/oc-netinst:protocols/oc-netinst:protocol/oc-netinst:bgp/oc-netinst:global/oc-netinst:state/oc-netinst:keepalive-interval {
      deviate add {
            sonic-ext:field-name "keepalive";
      }
    }

    deviation /oc-netinst:network-instances/oc-netinst:network-instance/oc-netinst:protocols/oc-netinst:protocol/oc-netinst:bgp/oc-netinst:global/oc-netinst:afi-safis/oc-netinst:afi-safi/oc-netinst:aggregate-address-config {
      deviate add {
        sonic-ext:table-name "NONE";
      }
    }

    deviation /oc-netinst:network-instances/oc-netinst:network-instance/oc-netinst:protocols/oc-netinst:protocol/oc-netinst:bgp/oc-netinst:global/oc-netinst:afi-safis/oc-netinst:afi-safi/oc-netinst:aggregate-address-config/oc-netinst:aggregate-address {
      deviate add {
        sonic-ext:table-name "BGP_GLOBALS_AF_AGGREGATE_ADDR";
        sonic-ext:key-transformer "bgp_gbl_afi_safi_addr_key_xfmr";
      }
    }

    deviation /oc-netinst:network-instances/oc-netinst:network-instance/oc-netinst:protocols/oc-netinst:protocol/oc-netinst:bgp/oc-netinst:global/oc-netinst:afi-safis/oc-netinst:afi-safi/oc-netinst:aggregate-address-config/oc-netinst:aggregate-address/oc-netinst:prefix {
      deviate add {
            sonic-ext:field-transformer "bgp_gbl_afi_safi_addr_field_xfmr";
            sonic-ext:field-name "ip_prefix";
      }
    }

    deviation /oc-netinst:network-instances/oc-netinst:network-instance/oc-netinst:protocols/oc-netinst:protocol/oc-netinst:bgp/oc-netinst:global/oc-netinst:afi-safis/oc-netinst:afi-safi/oc-netinst:aggregate-address-config/oc-netinst:aggregate-address/oc-netinst:config/oc-netinst:prefix {
      deviate add {
            sonic-ext:field-transformer "bgp_gbl_afi_safi_addr_field_xfmr";
            sonic-ext:field-name "ip_prefix";
      }
    }

    deviation /oc-netinst:network-instances/oc-netinst:network-instance/oc-netinst:protocols/oc-netinst:protocol/oc-netinst:bgp/oc-netinst:global/oc-netinst:afi-safis/oc-netinst:afi-safi/oc-netinst:aggregate-address-config/oc-netinst:aggregate-address/oc-netinst:state/oc-netinst:prefix {
      deviate add {
            sonic-ext:field-transformer "bgp_gbl_afi_safi_addr_field_xfmr";
            sonic-ext:field-name "ip_prefix";
      }
    }

    deviation /oc-netinst:network-instances/oc-netinst:network-instance/oc-netinst:protocols/oc-netinst:protocol/oc-netinst:bgp/oc-netinst:global/oc-netinst:afi-safis/oc-netinst:afi-safi/oc-netinst:aggregate-address-config/oc-netinst:aggregate-address/oc-netinst:config/oc-netinst:policy-name {
      deviate add {
            sonic-ext:field-name "policy";
      }
    }

    deviation /oc-netinst:network-instances/oc-netinst:network-instance/oc-netinst:protocols/oc-netinst:protocol/oc-netinst:bgp/oc-netinst:global/oc-netinst:afi-safis/oc-netinst:afi-safi/oc-netinst:aggregate-address-config/oc-netinst:aggregate-address/oc-netinst:state/oc-netinst:policy-name {
      deviate add {
            sonic-ext:field-name "policy";
      }
    }

    deviation /oc-netinst:network-instances/oc-netinst:network-instance/oc-netinst:protocols/oc-netinst:protocol/oc-netinst:bgp/oc-netinst:global/oc-netinst:afi-safis/oc-netinst:afi-safi/oc-netinst:aggregate-address-config/oc-netinst:aggregate-address/oc-netinst:config/oc-netinst:as-set {
      deviate add {
            sonic-ext:field-name "as_set";
      }
    }

    deviation /oc-netinst:network-instances/oc-netinst:network-instance/oc-netinst:protocols/oc-netinst:protocol/oc-netinst:bgp/oc-netinst:global/oc-netinst:afi-safis/oc-netinst:afi-safi/oc-netinst:aggregate-address-config/oc-netinst:aggregate-address/oc-netinst:state/oc-netinst:as-set {
      deviate add {
            sonic-ext:field-name "as_set";
      }
    }

    deviation /oc-netinst:network-instances/oc-netinst:network-instance/oc-netinst:protocols/oc-netinst:protocol/oc-netinst:bgp/oc-netinst:global/oc-netinst:afi-safis/oc-netinst:afi-safi/oc-netinst:aggregate-address-config/oc-netinst:aggregate-address/oc-netinst:config/oc-netinst:summary-only {
      deviate add {
            sonic-ext:field-name "summary_only";
      }
    }

    deviation /oc-netinst:network-instances/oc-netinst:network-instance/oc-netinst:protocols/oc-netinst:protocol/oc-netinst:bgp/oc-netinst:global/oc-netinst:afi-safis/oc-netinst:afi-safi/oc-netinst:aggregate-address-config/oc-netinst:aggregate-address/oc-netinst:state/oc-netinst:summary-only {
      deviate add {
            sonic-ext:field-name "summary_only";
      }
    }

    deviation /oc-netinst:network-instances/oc-netinst:network-instance/oc-netinst:protocols/oc-netinst:protocol/oc-netinst:bgp/oc-netinst:global/oc-netinst:afi-safis/oc-netinst:afi-safi/oc-netinst:default-route-distance/oc-netinst:config/oc-netinst:external-route-distance {
        deviate add {
            sonic-ext:field-name "ebgp_route_distance";
        }
    }

    deviation /oc-netinst:network-instances/oc-netinst:network-instance/oc-netinst:protocols/oc-netinst:protocol/oc-netinst:bgp/oc-netinst:global/oc-netinst:afi-safis/oc-netinst:afi-safi/oc-netinst:default-route-distance/oc-netinst:state/oc-netinst:external-route-distance {
        deviate add {
            sonic-ext:field-name "ebgp_route_distance";
        }
    }

    deviation /oc-netinst:network-instances/oc-netinst:network-instance/oc-netinst:protocols/oc-netinst:protocol/oc-netinst:bgp/oc-netinst:global/oc-netinst:afi-safis/oc-netinst:afi-safi/oc-netinst:default-route-distance/oc-netinst:config/oc-netinst:internal-route-distance {
        deviate add {
            sonic-ext:field-name "ibgp_route_distance";
        }
    }

    deviation /oc-netinst:network-instances/oc-netinst:network-instance/oc-netinst:protocols/oc-netinst:protocol/oc-netinst:bgp/oc-netinst:global/oc-netinst:afi-safis/oc-netinst:afi-safi/oc-netinst:default-route-distance/oc-netinst:state/oc-netinst:internal-route-distance {
        deviate add {
            sonic-ext:field-name "ibgp_route_distance";
        }
    }

    deviation /oc-netinst:network-instances/oc-netinst:network-instance/oc-netinst:protocols/oc-netinst:protocol/oc-netinst:bgp/oc-netinst:global/oc-netinst:afi-safis/oc-netinst:afi-safi/oc-netinst:default-route-distance/oc-netinst:config/oc-netinst:local-route-distance {
        deviate add {
            sonic-ext:field-name "local_route_distance";
        }
    }

    deviation /oc-netinst:network-instances/oc-netinst:network-instance/oc-netinst:protocols/oc-netinst:protocol/oc-netinst:bgp/oc-netinst:global/oc-netinst:afi-safis/oc-netinst:afi-safi/oc-netinst:default-route-distance/oc-netinst:state/oc-netinst:local-route-distance {
        deviate add {
            sonic-ext:field-name "local_route_distance";
        }
    }

    deviation /oc-netinst:network-instances/oc-netinst:network-instance/oc-netinst:protocols/oc-netinst:protocol/oc-netinst:bgp/oc-netinst:global/oc-netinst:afi-safis/oc-netinst:afi-safi/oc-bgp-ext:import-network-instance/oc-bgp-ext:config/oc-bgp-ext:name {
        deviate add {
            sonic-ext:field-name "import_vrf";
        }
    }

    deviation /oc-netinst:network-instances/oc-netinst:network-instance/oc-netinst:protocols/oc-netinst:protocol/oc-netinst:bgp/oc-netinst:global/oc-netinst:afi-safis/oc-netinst:afi-safi/oc-bgp-ext:import-network-instance/oc-bgp-ext:config/oc-bgp-ext:policy-name {
        deviate add {
            sonic-ext:field-name "import_vrf_route_map";
        }
    }

    deviation /oc-netinst:network-instances/oc-netinst:network-instance/oc-netinst:protocols/oc-netinst:protocol/oc-netinst:bgp/oc-netinst:global/oc-netinst:afi-safis/oc-netinst:afi-safi/oc-bgp-ext:import-network-instance/oc-bgp-ext:state/oc-bgp-ext:name {
        deviate add {
            sonic-ext:field-name "import_vrf";
        }
    }

    deviation /oc-netinst:network-instances/oc-netinst:network-instance/oc-netinst:protocols/oc-netinst:protocol/oc-netinst:bgp/oc-netinst:global/oc-netinst:afi-safis/oc-netinst:afi-safi/oc-bgp-ext:import-network-instance/oc-bgp-ext:state/oc-bgp-ext:policy-name {
        deviate add {
            sonic-ext:field-name "import_vrf_route_map";
        }
    }

    deviation /oc-netinst:network-instances/oc-netinst:network-instance/oc-netinst:protocols/oc-netinst:protocol/oc-netinst:bgp/oc-netinst:global/oc-netinst:afi-safis/oc-netinst:afi-safi/oc-netinst:network-config {
        deviate add {
            sonic-ext:table-name "NONE";
        }
    }

    deviation /oc-netinst:network-instances/oc-netinst:network-instance/oc-netinst:protocols/oc-netinst:protocol/oc-netinst:bgp/oc-netinst:global/oc-netinst:afi-safis/oc-netinst:afi-safi/oc-netinst:network-config/oc-netinst:network {
        deviate add {
            sonic-ext:table-name "BGP_GLOBALS_AF_NETWORK";
            sonic-ext:key-transformer "bgp_gbl_afi_safi_addr_key_xfmr";
        }
    }

    deviation /oc-netinst:network-instances/oc-netinst:network-instance/oc-netinst:protocols/oc-netinst:protocol/oc-netinst:bgp/oc-netinst:global/oc-netinst:afi-safis/oc-netinst:afi-safi/oc-netinst:network-config/oc-netinst:network/oc-netinst:prefix {
      deviate add {
            sonic-ext:field-transformer "bgp_gbl_afi_safi_addr_field_xfmr";
            sonic-ext:field-name "ip_prefix";
      }
    }

    deviation /oc-netinst:network-instances/oc-netinst:network-instance/oc-netinst:protocols/oc-netinst:protocol/oc-netinst:bgp/oc-netinst:global/oc-netinst:afi-safis/oc-netinst:afi-safi/oc-netinst:network-config/oc-netinst:network/oc-netinst:config/oc-netinst:prefix {
      deviate add {
            sonic-ext:field-transformer "bgp_gbl_afi_safi_addr_field_xfmr";
            sonic-ext:field-name "ip_prefix";
      }
    }

    deviation /oc-netinst:network-instances/oc-netinst:network-instance/oc-netinst:protocols/oc-netinst:protocol/oc-netinst:bgp/oc-netinst:global/oc-netinst:afi-safis/oc-netinst:afi-safi/oc-netinst:network-config/oc-netinst:network/oc-netinst:state/oc-netinst:prefix {
      deviate add {
            sonic-ext:field-transformer "bgp_gbl_afi_safi_addr_field_xfmr";
            sonic-ext:field-name "ip_prefix";
      }
    }

    deviation /oc-netinst:network-instances/oc-netinst:network-instance/oc-netinst:protocols/oc-netinst:protocol/oc-netinst:bgp/oc-netinst:global/oc-netinst:afi-safis/oc-netinst:afi-safi/oc-netinst:network-config/oc-netinst:network/oc-netinst:config/oc-netinst:policy-name {
      deviate add {
            sonic-ext:field-name "policy";
      }
    }

    deviation /oc-netinst:network-instances/oc-netinst:network-instance/oc-netinst:protocols/oc-netinst:protocol/oc-netinst:bgp/oc-netinst:global/oc-netinst:afi-safis/oc-netinst:afi-safi/oc-netinst:network-config/oc-netinst:network/oc-netinst:state/oc-netinst:policy-name {
      deviate add {
            sonic-ext:field-name "policy";
      }
    }

    deviation /oc-netinst:network-instances/oc-netinst:network-instance/oc-netinst:protocols/oc-netinst:protocol/oc-netinst:bgp/oc-netinst:global/oc-netinst:afi-safis/oc-netinst:afi-safi/oc-netinst:network-config/oc-netinst:network/oc-netinst:config/oc-netinst:backdoor {
      deviate add {
            sonic-ext:field-name "backdoor";
      }
    }

    deviation /oc-netinst:network-instances/oc-netinst:network-instance/oc-netinst:protocols/oc-netinst:protocol/oc-netinst:bgp/oc-netinst:global/oc-netinst:afi-safis/oc-netinst:afi-safi/oc-netinst:network-config/oc-netinst:network/oc-netinst:state/oc-netinst:backdoor {
      deviate add {
            sonic-ext:field-name "backdoor";
      }
    }

    deviation /oc-netinst:network-instances/oc-netinst:network-instance/oc-netinst:protocols/oc-netinst:protocol/oc-netinst:bgp/oc-netinst:global/oc-netinst:afi-safis/oc-netinst:afi-safi/oc-netinst:config/oc-netinst:table-map-name {
      deviate add {
            sonic-ext:field-name "route_download_filter";
      }
    }

    deviation /oc-netinst:network-instances/oc-netinst:network-instance/oc-netinst:protocols/oc-netinst:protocol/oc-netinst:bgp/oc-netinst:global/oc-netinst:afi-safis/oc-netinst:afi-safi/oc-netinst:state/oc-netinst:table-map-name {
      deviate add {
            sonic-ext:field-name "route_download_filter";
      }
    }
 
/* BGP Neighbors */
    deviation /oc-netinst:network-instances/oc-netinst:network-instance/oc-netinst:protocols/oc-netinst:protocol/oc-netinst:bgp/oc-netinst:neighbors/oc-netinst:neighbor {
      deviate add {
        sonic-ext:table-transformer "bgp_nbr_tbl_xfmr";
        sonic-ext:key-transformer "bgp_nbr_tbl_key_xfmr";
        sonic-ext:path-transformer "bgp_nbr_path_xfmr";
        sonic-ext:data-source "dynamic";
      }
    }

    deviation /oc-netinst:network-instances/oc-netinst:network-instance/oc-netinst:protocols/oc-netinst:protocol/oc-netinst:bgp/oc-netinst:neighbors/oc-netinst:neighbor/oc-netinst:config/oc-netinst:neighbor-address {
      deviate add {
            sonic-ext:field-transformer "bgp_nbr_address_fld_xfmr";
            sonic-ext:field-name "neighbor";
      }
    }

    deviation /oc-netinst:network-instances/oc-netinst:network-instance/oc-netinst:protocols/oc-netinst:protocol/oc-netinst:bgp/oc-netinst:neighbors/oc-netinst:neighbor/oc-netinst:config/oc-netinst:enabled {
      deviate add {
            sonic-ext:field-name "admin_status";
      }
    }

    deviation /oc-netinst:network-instances/oc-netinst:network-instance/oc-netinst:protocols/oc-netinst:protocol/oc-netinst:bgp/oc-netinst:neighbors/oc-netinst:neighbor/oc-netinst:config/oc-netinst:peer-group {
      deviate add {
            sonic-ext:field-name "peer_group_name";
      }
    }

/* neighbor->ebgp-multihop */
    deviation /oc-netinst:network-instances/oc-netinst:network-instance/oc-netinst:protocols/oc-netinst:protocol/oc-netinst:bgp/oc-netinst:neighbors/oc-netinst:neighbor/oc-netinst:ebgp-multihop/oc-netinst:config/oc-netinst:multihop-ttl {
      deviate add {
            sonic-ext:field-name "ebgp_multihop_ttl";
      }
    }

    deviation /oc-netinst:network-instances/oc-netinst:network-instance/oc-netinst:protocols/oc-netinst:protocol/oc-netinst:bgp/oc-netinst:neighbors/oc-netinst:neighbor/oc-netinst:ebgp-multihop/oc-netinst:config/oc-netinst:enabled {
      deviate add {
            sonic-ext:field-name "ebgp_multihop";
      }
    }

/* neighbor->ebgp-multihop>state */
    deviation /oc-netinst:network-instances/oc-netinst:network-instance/oc-netinst:protocols/oc-netinst:protocol/oc-netinst:bgp/oc-netinst:neighbors/oc-netinst:neighbor/oc-netinst:ebgp-multihop/oc-netinst:state/oc-netinst:multihop-ttl {
      deviate add {
            sonic-ext:field-name "ebgp_multihop_ttl";
      }
    }

    deviation /oc-netinst:network-instances/oc-netinst:network-instance/oc-netinst:protocols/oc-netinst:protocol/oc-netinst:bgp/oc-netinst:neighbors/oc-netinst:neighbor/oc-netinst:ebgp-multihop/oc-netinst:state/oc-netinst:enabled {
      deviate add {
            sonic-ext:field-name "ebgp_multihop";
      }
    }

/* neighbor->timers->config */
/* neighbor->timers->config->minimum-advertisement-interval */
    deviation /oc-netinst:network-instances/oc-netinst:network-instance/oc-netinst:protocols/oc-netinst:protocol/oc-netinst:bgp/oc-netinst:neighbors/oc-netinst:neighbor/oc-netinst:timers/oc-netinst:config/oc-netinst:minimum-advertisement-interval {
      deviate add {
            sonic-ext:field-name "min_adv_interval";
      }
    }

/* neighbor->timers->config->connect-retry */
    deviation /oc-netinst:network-instances/oc-netinst:network-instance/oc-netinst:protocols/oc-netinst:protocol/oc-netinst:bgp/oc-netinst:neighbors/oc-netinst:neighbor/oc-netinst:timers/oc-netinst:config/oc-netinst:connect-retry {
      deviate add {
            sonic-ext:field-name "conn_retry";
      }
    }

/* neighbor->timers->config->hold-time */
    deviation /oc-netinst:network-instances/oc-netinst:network-instance/oc-netinst:protocols/oc-netinst:protocol/oc-netinst:bgp/oc-netinst:neighbors/oc-netinst:neighbor/oc-netinst:timers/oc-netinst:config/oc-netinst:hold-time {
      deviate add {
            sonic-ext:field-name "holdtime";
      }
    }

/* neighbor->timers->config->keepalive-interval */
    deviation /oc-netinst:network-instances/oc-netinst:network-instance/oc-netinst:protocols/oc-netinst:protocol/oc-netinst:bgp/oc-netinst:neighbors/oc-netinst:neighbor/oc-netinst:timers/oc-netinst:config/oc-netinst:keepalive-interval {
      deviate add {
            sonic-ext:field-name "keepalive";
      }
    }

/* neighbor->config */
/* neighbor->config->description */
    deviation /oc-netinst:network-instances/oc-netinst:network-instance/oc-netinst:protocols/oc-netinst:protocol/oc-netinst:bgp/oc-netinst:neighbors/oc-netinst:neighbor/oc-netinst:config/oc-netinst:description {
      deviate add {
            sonic-ext:field-name "name";
      }
    }

/* neighbor->config->peer-as */
    deviation /oc-netinst:network-instances/oc-netinst:network-instance/oc-netinst:protocols/oc-netinst:protocol/oc-netinst:bgp/oc-netinst:neighbors/oc-netinst:neighbor/oc-netinst:config/oc-netinst:peer-as {
      deviate add {
            sonic-ext:field-transformer "bgp_nbr_asn_fld_xfmr";
            sonic-ext:field-name "asn";
      }
    }

/* neighbor->config->peer-type */
    deviation /oc-netinst:network-instances/oc-netinst:network-instance/oc-netinst:protocols/oc-netinst:protocol/oc-netinst:bgp/oc-netinst:neighbors/oc-netinst:neighbor/oc-netinst:config/oc-netinst:peer-type {
      deviate add {
            sonic-ext:field-transformer "bgp_nbr_peer_type_fld_xfmr";
            sonic-ext:field-name "peer_type";
      }
    }

/* neighbor->config->local-as */
    deviation /oc-netinst:network-instances/oc-netinst:network-instance/oc-netinst:protocols/oc-netinst:protocol/oc-netinst:bgp/oc-netinst:neighbors/oc-netinst:neighbor/oc-netinst:config/oc-netinst:local-as {
      deviate add {
            sonic-ext:field-transformer "bgp_nbr_local_asn_fld_xfmr";
            sonic-ext:field-name "local_asn";
      }
    }

/* neighbor->transport->config */
/* neighbor->transport->config->passive-mode */
    deviation /oc-netinst:network-instances/oc-netinst:network-instance/oc-netinst:protocols/oc-netinst:protocol/oc-netinst:bgp/oc-netinst:neighbors/oc-netinst:neighbor/oc-netinst:transport/oc-netinst:config/oc-netinst:passive-mode {
      deviate add {
            sonic-ext:field-name "passive_mode";
      }
    }

/* neighbor->transport->config->local-address */
    deviation /oc-netinst:network-instances/oc-netinst:network-instance/oc-netinst:protocols/oc-netinst:protocol/oc-netinst:bgp/oc-netinst:neighbors/oc-netinst:neighbor/oc-netinst:transport/oc-netinst:config/oc-netinst:local-address {
      deviate add {
            sonic-ext:field-name "local_addr";
      }
    }

/* BGP NBR AFI SAFI */
    deviation /oc-netinst:network-instances/oc-netinst:network-instance/oc-netinst:protocols/oc-netinst:protocol/oc-netinst:bgp/oc-netinst:neighbors/oc-netinst:neighbor/oc-netinst:afi-safis {
      deviate add {
        sonic-ext:table-name "NONE";
      }
    }

    deviation /oc-netinst:network-instances/oc-netinst:network-instance/oc-netinst:protocols/oc-netinst:protocol/oc-netinst:bgp/oc-netinst:neighbors/oc-netinst:neighbor/oc-netinst:afi-safis/oc-netinst:afi-safi {
      deviate add {
        sonic-ext:table-transformer "bgp_af_nbr_tbl_xfmr";
        sonic-ext:key-transformer "bgp_af_nbr_tbl_key_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-netinst:enabled {
      deviate add {
        sonic-ext:field-name "admin_status";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn {
      deviate add {
        sonic-ext:get-validate "bgp_validate_nbr_af";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast {
      deviate add {
        sonic-ext:get-validate "bgp_validate_nbr_af";
      }
    }
    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast {
      deviate add {
        sonic-ext:get-validate "bgp_validate_nbr_af";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-netinst:afi-safi-name {
      deviate add {
            sonic-ext:field-transformer "bgp_nbr_afi_safi_name_fld_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:config/oc-netinst:send-default-route {
      deviate add {
            sonic-ext:field-name "send_default_route";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:state/oc-netinst:send-default-route {
      deviate add {
            sonic-ext:field-name "send_default_route";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:config/oc-netinst:max-prefixes {
      deviate add {
            sonic-ext:field-name "max_prefix_limit";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:config/oc-netinst:prevent-teardown {
      deviate add {
            sonic-ext:field-name "max_prefix_warning_only";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:config/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:config/oc-netinst:restart-timer {
      deviate add {
            sonic-ext:field-name "max_prefix_restart_interval";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:config/oc-netinst:restart-timer {
      deviate add {
            sonic-ext:field-name "max_prefix_restart_interval";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:config/oc-netinst:max-prefixes {
      deviate add {
            sonic-ext:field-name "max_prefix_limit";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:config/oc-netinst:prevent-teardown {
      deviate add {
            sonic-ext:field-name "max_prefix_warning_only";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:config/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:config/oc-netinst:send-default-route {
      deviate add {
            sonic-ext:field-name "send_default_route";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:config/oc-netinst:import-policy {
      deviate add {
            sonic-ext:field-name "route_map_in";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:config/oc-netinst:export-policy {
      deviate add {
            sonic-ext:field-name "route_map_out";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:state/oc-netinst:max-prefixes {
      deviate add {
            sonic-ext:field-name "max_prefix_limit";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:state/oc-netinst:prevent-teardown {
      deviate add {
            sonic-ext:field-name "max_prefix_warning_only";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:state/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:state/oc-netinst:restart-timer {
      deviate add {
            sonic-ext:field-name "max_prefix_restart_interval";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:state/oc-netinst:restart-timer {
      deviate add {
            sonic-ext:field-name "max_prefix_restart_interval";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:state/oc-netinst:max-prefixes {
      deviate add {
            sonic-ext:field-name "max_prefix_limit";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:state/oc-netinst:prevent-teardown {
      deviate add {
            sonic-ext:field-name "max_prefix_warning_only";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:state/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:state/oc-netinst:send-default-route {
      deviate add {
            sonic-ext:field-name "send_default_route";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:state/oc-netinst:import-policy {
      deviate add {
            sonic-ext:field-name "route_map_in";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:state/oc-netinst:export-policy {
      deviate add {
            sonic-ext:field-name "route_map_out";
      }
    }
/* BGP Extended attrs for NBR and Peer group */

    deviation /oc-netinst:network-instances/oc-netinst:network-instance/oc-netinst:protocols/oc-netinst:protocol/oc-netinst:bgp/oc-netinst:neighbors/oc-netinst:neighbor/oc-netinst:config/oc-netinst:disable-ebgp-connected-route-check {
      deviate add {
        sonic-ext:field-name "disable_ebgp_connected_route_check";
      }
    }

    deviation /oc-netinst:network-instances/oc-netinst:network-instance/oc-netinst:protocols/oc-netinst:protocol/oc-netinst:bgp/oc-netinst:neighbors/oc-netinst:neighbor/oc-netinst:config/oc-netinst:enforce-first-as {
      deviate add {
        sonic-ext:field-name "enforce_first_as";
      }
    }

    deviation /oc-netinst:network-instances/oc-netinst:network-instance/oc-netinst:protocols/oc-netinst:protocol/oc-netinst:bgp/oc-netinst:neighbors/oc-netinst:neighbor/oc-netinst:config/oc-netinst:solo-peer {
      deviate add {
        sonic-ext:field-name "solo_peer";
      }
    }

    deviation /oc-netinst:network-instances/oc-netinst:network-instance/oc-netinst:protocols/oc-netinst:protocol/oc-netinst:bgp/oc-netinst:neighbors/oc-netinst:neighbor/oc-netinst:config/oc-netinst:ttl-security-hops {
      deviate add {
        sonic-ext:field-name "ttl_security_hops";
      }
    }

    deviation /oc-netinst:network-instances/oc-netinst:network-instance/oc-netinst:protocols/oc-netinst:protocol/oc-netinst:bgp/oc-netinst:neighbors/oc-netinst:neighbor/oc-netinst:config/oc-netinst:capability-extended-nexthop {
      deviate add {
        sonic-ext:field-name "capability_ext_nexthop";
      }
    }

    deviation /oc-netinst:network-instances/oc-netinst:network-instance/oc-netinst:protocols/oc-netinst:protocol/oc-netinst:bgp/oc-netinst:neighbors/oc-netinst:neighbor/oc-netinst:enable-bfd/oc-netinst:config/oc-netinst:enabled {
      deviate add {
        sonic-ext:field-name "bfd";
      }
    }

    deviation /oc-netinst:network-instances/oc-netinst:network-instance/oc-netinst:protocols/oc-netinst:protocol/oc-netinst:bgp/oc-netinst:neighbors/oc-netinst:neighbor/oc-netinst:enable-bfd/oc-netinst:config/oc-netinst:check-control-plane-failure {
      deviate add {
        sonic-ext:field-transformer "bgp_nbr_bfd_check_ctrl_plane_failure_fld_xfmr";
        sonic-ext:field-name "bfd_check_ctrl_plane_failure";
      }
    }

    deviation /oc-netinst:network-instances/oc-netinst:network-instance/oc-netinst:protocols/oc-netinst:protocol/oc-netinst:bgp/oc-netinst:neighbors/oc-netinst:neighbor/oc-netinst:enable-bfd/oc-netinst:config/oc-netinst:bfd-profile {
      deviate add {
        sonic-ext:field-transformer "bgp_nbr_bfd_profile_fld_xfmr";
        sonic-ext:field-name "bfd_profile";
      }
    }

    deviation /oc-netinst:network-instances/oc-netinst:network-instance/oc-netinst:protocols/oc-netinst:protocol/oc-netinst:bgp/oc-netinst:neighbors/oc-netinst:neighbor/oc-netinst:enable-bfd/oc-netinst:state/oc-netinst:enabled {
      deviate add {
        sonic-ext:field-name "bfd";
      }
    }

    deviation /oc-netinst:network-instances/oc-netinst:network-instance/oc-netinst:protocols/oc-netinst:protocol/oc-netinst:bgp/oc-netinst:neighbors/oc-netinst:neighbor/oc-netinst:enable-bfd/oc-netinst:state/oc-netinst:check-control-plane-failure {
      deviate add {
        sonic-ext:field-name "bfd_check_ctrl_plane_failure";
      }
    }

    deviation /oc-netinst:network-instances/oc-netinst:network-instance/oc-netinst:protocols/oc-netinst:protocol/oc-netinst:bgp/oc-netinst:neighbors/oc-netinst:neighbor/oc-netinst:enable-bfd/oc-netinst:state/oc-netinst:bfd-profile {
      deviate add {
        sonic-ext:field-name "bfd_profile";
      }
    }

    deviation /oc-netinst:network-instances/oc-netinst:network-instance/oc-netinst:protocols/oc-netinst:protocol/oc-netinst:bgp/oc-netinst:neighbors/oc-netinst:neighbor/oc-netinst:config/oc-netinst:capability-dynamic {
      deviate add {
        sonic-ext:field-name "capability_dynamic";
      }
    }

    deviation /oc-netinst:network-instances/oc-netinst:network-instance/oc-netinst:protocols/oc-netinst:protocol/oc-netinst:bgp/oc-netinst:neighbors/oc-netinst:neighbor/oc-netinst:config/oc-netinst:dont-negotiate-capability {
      deviate add {
        sonic-ext:field-name "dont_negotiate_capability";
      }
    }

    deviation /oc-netinst:network-instances/oc-netinst:network-instance/oc-netinst:protocols/oc-netinst:protocol/oc-netinst:bgp/oc-netinst:neighbors/oc-netinst:neighbor/oc-netinst:config/oc-netinst:enforce-multihop {
      deviate add {
        sonic-ext:field-name "enforce_multihop";
      }
    }

    deviation /oc-netinst:network-instances/oc-netinst:network-instance/oc-netinst:protocols/oc-netinst:protocol/oc-netinst:bgp/oc-netinst:neighbors/oc-netinst:neighbor/oc-netinst:config/oc-netinst:override-capability {
      deviate add {
        sonic-ext:field-name "override_capability";
      }
    }

    deviation /oc-netinst:network-instances/oc-netinst:network-instance/oc-netinst:protocols/oc-netinst:protocol/oc-netinst:bgp/oc-netinst:neighbors/oc-netinst:neighbor/oc-netinst:config/oc-netinst:peer-port {
      deviate add {
        sonic-ext:field-name "peer_port";
      }
    }

    deviation /oc-netinst:network-instances/oc-netinst:network-instance/oc-netinst:protocols/oc-netinst:protocol/oc-netinst:bgp/oc-netinst:neighbors/oc-netinst:neighbor/oc-netinst:config/oc-netinst:shutdown-message {
      deviate add {
        sonic-ext:field-name "shutdown_message";
      }
    }

    deviation /oc-netinst:network-instances/oc-netinst:network-instance/oc-netinst:protocols/oc-netinst:protocol/oc-netinst:bgp/oc-netinst:neighbors/oc-netinst:neighbor/oc-netinst:config/oc-netinst:strict-capability-match {
      deviate add {
        sonic-ext:field-name "strict_capability_match";
      }
    }

    deviation /oc-netinst:network-instances/oc-netinst:network-instance/oc-netinst:protocols/oc-netinst:protocol/oc-netinst:bgp/oc-netinst:neighbors/oc-netinst:neighbor/oc-netinst:config/oc-netinst:local-as-no-prepend {
      deviate add {
        sonic-ext:field-name "local_as_no_prepend";
      }
    }

    deviation /oc-netinst:network-instances/oc-netinst:network-instance/oc-netinst:protocols/oc-netinst:protocol/oc-netinst:bgp/oc-netinst:neighbors/oc-netinst:neighbor/oc-netinst:config/oc-netinst:local-as-replace-as {
      deviate add {
        sonic-ext:field-name "local_as_replace_as";
      }
    }

    deviation /oc-netinst:network-instances/oc-netinst:network-instance/oc-netinst:protocols/oc-netinst:protocol/oc-netinst:bgp/oc-netinst:peer-groups/oc-netinst:peer-group/oc-netinst:config/oc-netinst:disable-ebgp-connected-route-check {
      deviate add {
        sonic-ext:field-name "disable_ebgp_connected_route_check";
      }
    }

    deviation /oc-netinst:network-instances/oc-netinst:network-instance/oc-netinst:protocols/oc-netinst:protocol/oc-netinst:bgp/oc-netinst:peer-groups/oc-netinst:peer-group/oc-netinst:config/oc-netinst:enforce-first-as {
      deviate add {
        sonic-ext:field-name "enforce_first_as";
      }
    }

    deviation /oc-netinst:network-instances/oc-netinst:network-instance/oc-netinst:protocols/oc-netinst:protocol/oc-netinst:bgp/oc-netinst:peer-groups/oc-netinst:peer-group/oc-netinst:config/oc-netinst:solo-peer {
      deviate add {
        sonic-ext:field-name "solo_peer";
      }
    }

    deviation /oc-netinst:network-instances/oc-netinst:network-instance/oc-netinst:protocols/oc-netinst:protocol/oc-netinst:bgp/oc-netinst:peer-groups/oc-netinst:peer-group/oc-netinst:config/oc-netinst:ttl-security-hops {
      deviate add {
        sonic-ext:field-name "ttl_security_hops";
      }
    }

    deviation /oc-netinst:network-instances/oc-netinst:network-instance/oc-netinst:protocols/oc-netinst:protocol/oc-netinst:bgp/oc-netinst:peer-groups/oc-netinst:peer-group/oc-netinst:config/oc-netinst:capability-extended-nexthop {
      deviate add {
        sonic-ext:field-name "capability_ext_nexthop";
      }
    }

    deviation /oc-netinst:network-instances/oc-netinst:network-instance/oc-netinst:protocols/oc-netinst:protocol/oc-netinst:bgp/oc-netinst:peer-groups/oc-netinst:peer-group/oc-netinst:enable-bfd/oc-netinst:config/oc-netinst:enabled {
      deviate add {
        sonic-ext:field-name "bfd";
      }
    }

    deviation /oc-netinst:network-instances/oc-netinst:network-instance/oc-netinst:protocols/oc-netinst:protocol/oc-netinst:bgp/oc-netinst:peer-groups/oc-netinst:peer-group/oc-netinst:enable-bfd/oc-netinst:config/oc-netinst:check-control-plane-failure {
      deviate add {
        sonic-ext:field-name "bfd_check_ctrl_plane_failure";
      }
    }

    deviation /oc-netinst:network-instances/oc-netinst:network-instance/oc-netinst:protocols/oc-netinst:protocol/oc-netinst:bgp/oc-netinst:peer-groups/oc-netinst:peer-group/oc-netinst:enable-bfd/oc-netinst:config/oc-netinst:bfd-profile {
      deviate add {
        sonic-ext:field-name "bfd_profile";
      }
    }

    deviation /oc-netinst:network-instances/oc-netinst:network-instance/oc-netinst:protocols/oc-netinst:protocol/oc-netinst:bgp/oc-netinst:peer-groups/oc-netinst:peer-group/oc-netinst:state/oc-netinst:disable-ebgp-connected-route-check {
      deviate add {
        sonic-ext:field-name "disable_ebgp_connected_route_check";
      }
    }

    deviation /oc-netinst:network-instances/oc-netinst:network-instance/oc-netinst:protocols/oc-netinst:protocol/oc-netinst:bgp/oc-netinst:peer-groups/oc-netinst:peer-group/oc-netinst:state/oc-netinst:enforce-first-as {
      deviate add {
        sonic-ext:field-name "enforce_first_as";
      }
    }

    deviation /oc-netinst:network-instances/oc-netinst:network-instance/oc-netinst:protocols/oc-netinst:protocol/oc-netinst:bgp/oc-netinst:peer-groups/oc-netinst:peer-group/oc-netinst:state/oc-netinst:solo-peer {
      deviate add {
        sonic-ext:field-name "solo_peer";
      }
    }

    deviation /oc-netinst:network-instances/oc-netinst:network-instance/oc-netinst:protocols/oc-netinst:protocol/oc-netinst:bgp/oc-netinst:peer-groups/oc-netinst:peer-group/oc-netinst:state/oc-netinst:ttl-security-hops {
      deviate add {
        sonic-ext:field-name "ttl_security_hops";
      }
    }

    deviation /oc-netinst:network-instances/oc-netinst:network-instance/oc-netinst:protocols/oc-netinst:protocol/oc-netinst:bgp/oc-netinst:peer-groups/oc-netinst:peer-group/oc-netinst:state/oc-netinst:capability-extended-nexthop {
      deviate add {
        sonic-ext:field-name "capability_ext_nexthop";
      }
    }

    deviation /oc-netinst:network-instances/oc-netinst:network-instance/oc-netinst:protocols/oc-netinst:protocol/oc-netinst:bgp/oc-netinst:peer-groups/oc-netinst:peer-group/oc-netinst:enable-bfd/oc-netinst:state/oc-netinst:enabled {
      deviate add {
        sonic-ext:field-name "bfd";
      }
    }

    deviation /oc-netinst:network-instances/oc-netinst:network-instance/oc-netinst:protocols/oc-netinst:protocol/oc-netinst:bgp/oc-netinst:peer-groups/oc-netinst:peer-group/oc-netinst:enable-bfd/oc-netinst:state/oc-netinst:check-control-plane-failure {
      deviate add {
        sonic-ext:field-name "bfd_check_ctrl_plane_failure";
      }
    }

    deviation /oc-netinst:network-instances/oc-netinst:network-instance/oc-netinst:protocols/oc-netinst:protocol/oc-netinst:bgp/oc-netinst:peer-groups/oc-netinst:peer-group/oc-netinst:enable-bfd/oc-netinst:state/oc-netinst:bfd-profile {
      deviate add {
        sonic-ext:field-name "bfd_profile";
      }
    }

    deviation /oc-netinst:network-instances/oc-netinst:network-instance/oc-netinst:protocols/oc-netinst:protocol/oc-netinst:bgp/oc-netinst:peer-groups/oc-netinst:peer-group/oc-netinst:config/oc-netinst:capability-dynamic {
      deviate add {
        sonic-ext:field-name "capability_dynamic";
      }
    }

    deviation /oc-netinst:network-instances/oc-netinst:network-instance/oc-netinst:protocols/oc-netinst:protocol/oc-netinst:bgp/oc-netinst:peer-groups/oc-netinst:peer-group/oc-netinst:config/oc-netinst:dont-negotiate-capability {
      deviate add {
        sonic-ext:field-name "dont_negotiate_capability";
      }
    }

    deviation /oc-netinst:network-instances/oc-netinst:network-instance/oc-netinst:protocols/oc-netinst:protocol/oc-netinst:bgp/oc-netinst:peer-groups/oc-netinst:peer-group/oc-netinst:config/oc-netinst:enforce-multihop {
      deviate add {
        sonic-ext:field-name "enforce_multihop";
      }
    }

    deviation /oc-netinst:network-instances/oc-netinst:network-instance/oc-netinst:protocols/oc-netinst:protocol/oc-netinst:bgp/oc-netinst:peer-groups/oc-netinst:peer-group/oc-netinst:config/oc-netinst:override-capability {
      deviate add {
        sonic-ext:field-name "override_capability";
      }
    }

    deviation /oc-netinst:network-instances/oc-netinst:network-instance/oc-netinst:protocols/oc-netinst:protocol/oc-netinst:bgp/oc-netinst:peer-groups/oc-netinst:peer-group/oc-netinst:config/oc-netinst:peer-port {
      deviate add {
        sonic-ext:field-name "peer_port";
      }
    }

    deviation /oc-netinst:network-instances/oc-netinst:network-instance/oc-netinst:protocols/oc-netinst:protocol/oc-netinst:bgp/oc-netinst:peer-groups/oc-netinst:peer-group/oc-netinst:config/oc-netinst:shutdown-message {
      deviate add {
        sonic-ext:field-name "shutdown_message";
      }
    }

    deviation /oc-netinst:network-instances/oc-netinst:network-instance/oc-netinst:protocols/oc-netinst:protocol/oc-netinst:bgp/oc-netinst:peer-groups/oc-netinst:peer-group/oc-netinst:config/oc-netinst:strict-capability-match {
      deviate add {
        sonic-ext:field-name "strict_capability_match";
      }
    }

    deviation /oc-netinst:network-instances/oc-netinst:network-instance/oc-netinst:protocols/oc-netinst:protocol/oc-netinst:bgp/oc-netinst:peer-groups/oc-netinst:peer-group/oc-netinst:config/oc-netinst:local-as-no-prepend {
      deviate add {
        sonic-ext:field-name "local_as_no_prepend";
      }
    }

    deviation /oc-netinst:network-instances/oc-netinst:network-instance/oc-netinst:protocols/oc-netinst:protocol/oc-netinst:bgp/oc-netinst:peer-groups/oc-netinst:peer-group/oc-netinst:config/oc-netinst:local-as-replace-as {
      deviate add {
        sonic-ext:field-name "local_as_replace_as";
      }
    }


    deviation /oc-netinst:network-instances/oc-netinst:network-instance/oc-netinst:protocols/oc-netinst:protocol/oc-netinst:bgp/oc-netinst:peer-groups/oc-netinst:peer-group/oc-netinst:state/oc-netinst:capability-dynamic {
      deviate add {
        sonic-ext:field-name "capability_dynamic";
      }
    }

    deviation /oc-netinst:network-instances/oc-netinst:network-instance/oc-netinst:protocols/oc-netinst:protocol/oc-netinst:bgp/oc-netinst:peer-groups/oc-netinst:peer-group/oc-netinst:state/oc-netinst:dont-negotiate-capability {
      deviate add {
        sonic-ext:field-name "dont_negotiate_capability";
      }
    }

    deviation /oc-netinst:network-instances/oc-netinst:network-instance/oc-netinst:protocols/oc-netinst:protocol/oc-netinst:bgp/oc-netinst:peer-groups/oc-netinst:peer-group/oc-netinst:state/oc-netinst:enforce-multihop {
      deviate add {
        sonic-ext:field-name "enforce_multihop";
      }
    }

    deviation /oc-netinst:network-instances/oc-netinst:network-instance/oc-netinst:protocols/oc-netinst:protocol/oc-netinst:bgp/oc-netinst:peer-groups/oc-netinst:peer-group/oc-netinst:state/oc-netinst:override-capability {
      deviate add {
        sonic-ext:field-name "override_capability";
      }
    }

    deviation /oc-netinst:network-instances/oc-netinst:network-instance/oc-netinst:protocols/oc-netinst:protocol/oc-netinst:bgp/oc-netinst:peer-groups/oc-netinst:peer-group/oc-netinst:state/oc-netinst:peer-port {
      deviate add {
        sonic-ext:field-name "peer_port";
      }
    }

    deviation /oc-netinst:network-instances/oc-netinst:network-instance/oc-netinst:protocols/oc-netinst:protocol/oc-netinst:bgp/oc-netinst:peer-groups/oc-netinst:peer-group/oc-netinst:state/oc-netinst:shutdown-message {
      deviate add {
        sonic-ext:field-name "shutdown_message";
      }
    }

    deviation /oc-netinst:network-instances/oc-netinst:network-instance/oc-netinst:protocols/oc-netinst:protocol/oc-netinst:bgp/oc-netinst:peer-groups/oc-netinst:peer-group/oc-netinst:state/oc-netinst:strict-capability-match {
      deviate add {
        sonic-ext:field-name "strict_capability_match";
      }
    }

    deviation /oc-netinst:network-instances/oc-netinst:network-instance/oc-netinst:protocols/oc-netinst:protocol/oc-netinst:bgp/oc-netinst:peer-groups/oc-netinst:peer-group/oc-netinst:state/oc-netinst:local-as-no-prepend {
      deviate add {
        sonic-ext:field-name "local_as_no_prepend";
      }
    }

    deviation /oc-netinst:network-instances/oc-netinst:network-instance/oc-netinst:protocols/oc-netinst:protocol/oc-netinst:bgp/oc-netinst:peer-groups/oc-netinst:peer-group/oc-netinst:state/oc-netinst:local-as-replace-as {
      deviate add {
        sonic-ext:field-name "local_as_replace_as";
      }
    }



/* BGP Extended attrs for NBR and Peer group AFI_SAFI */

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-netinst:soft-reconfiguration-in {
      deviate add {
        sonic-ext:field-name "soft_reconfiguration_in";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-netinst:unsuppress-map-name {
      deviate add {
        sonic-ext:field-name "unsuppress_map_name";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-netinst:weight {
      deviate add {
        sonic-ext:field-name "weight";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-netinst:as-override {
      deviate add {
        sonic-ext:field-name "as_override";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-netinst:send-community {
      deviate add {
        sonic-ext:field-transformer "bgp_nbr_community_type_fld_xfmr";
        sonic-ext:field-name  "send_community";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-netinst:route-reflector-client {
      deviate add {
        sonic-ext:field-name "rrclient";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-netinst:route-server-client {
      deviate add {
        sonic-ext:field-name "route_server_client";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-netinst:fabric-external {
      deviate add {
        sonic-ext:field-name "fabric_external";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:add-paths/oc-netinst:config/oc-netinst:tx-add-paths {
      deviate add {
        sonic-ext:field-transformer "bgp_nbr_tx_add_paths_fld_xfmr";
        sonic-ext:field-name "tx_add_paths";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:add-paths/oc-netinst:state/oc-netinst:tx-add-paths {
      deviate add {
        sonic-ext:field-transformer "bgp_nbr_tx_add_paths_fld_xfmr";
        sonic-ext:field-name "tx_add_paths";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:add-paths/oc-netinst:config/oc-netinst:tx-add-paths {
      deviate add {
        sonic-ext:field-transformer "bgp_pgrp_tx_add_paths_fld_xfmr";
        sonic-ext:field-name "tx_add_paths";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:add-paths/oc-netinst:state/oc-netinst:tx-add-paths {
      deviate add {
        sonic-ext:field-transformer "bgp_pgrp_tx_add_paths_fld_xfmr";
        sonic-ext:field-name "tx_add_paths";
      }
    }


    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-netinst:soft-reconfiguration-in {
      deviate add {
        sonic-ext:field-name "soft_reconfiguration_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-netinst:unsuppress-map-name {
      deviate add {
        sonic-ext:field-name "unsuppress_map_name";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-netinst:weight {
      deviate add {
        sonic-ext:field-name "weight";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-netinst:as-override {
      deviate add {
        sonic-ext:field-name "as_override";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-netinst:send-community {
      deviate add {
        sonic-ext:field-transformer "bgp_pgrp_community_type_fld_xfmr";
        sonic-ext:field-name "send_community";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-netinst:route-reflector-client {
      deviate add {
        sonic-ext:field-name "rrclient";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-netinst:route-server-client {
      deviate add {
        sonic-ext:field-name "route_server_client";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-netinst:fabric-external {
      deviate add {
        sonic-ext:field-name "fabric_external";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-netinst:soft-reconfiguration-in {
      deviate add {
        sonic-ext:field-name "soft_reconfiguration_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-netinst:unsuppress-map-name {
      deviate add {
        sonic-ext:field-name "unsuppress_map_name";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-netinst:weight {
      deviate add {
        sonic-ext:field-name "weight";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-netinst:as-override {
      deviate add {
        sonic-ext:field-name "as_override";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-netinst:send-community {
      deviate add {
        sonic-ext:field-transformer "bgp_pgrp_community_type_fld_xfmr";
        sonic-ext:field-name "send_community";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-netinst:route-reflector-client {
      deviate add {
        sonic-ext:field-name "rrclient";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-netinst:route-server-client {
      deviate add {
        sonic-ext:field-name "route_server_client";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-netinst:fabric-external {
      deviate add {
        sonic-ext:field-name "fabric_external";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:allow-own-as/oc-netinst:config/oc-netinst:enabled {
      deviate add {
        sonic-ext:field-name "allow_as_in";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:allow-own-as/oc-netinst:config/oc-netinst:as-count {
      deviate add {
        sonic-ext:field-name "allow_as_count";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:allow-own-as/oc-netinst:config/oc-netinst:origin {
      deviate add {
        sonic-ext:field-name "allow_as_origin";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:allow-own-as/oc-netinst:state/oc-netinst:enabled {
      deviate add {
        sonic-ext:field-name "allow_as_in";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:allow-own-as/oc-netinst:state/oc-netinst:as-count {
      deviate add {
        sonic-ext:field-name "allow_as_count";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:allow-own-as/oc-netinst:state/oc-netinst:origin {
      deviate add {
        sonic-ext:field-name "allow_as_origin";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:attribute-unchanged/oc-netinst:config/oc-netinst:as-path {
      deviate add {
        sonic-ext:field-name "unchanged_as_path";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:attribute-unchanged/oc-netinst:config/oc-netinst:med {
      deviate add {
        sonic-ext:field-name "unchanged_med";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:attribute-unchanged/oc-netinst:config/oc-netinst:next-hop {
      deviate add {
        sonic-ext:field-name "unchanged_nexthop";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:attribute-unchanged/oc-netinst:state/oc-netinst:as-path {
      deviate add {
        sonic-ext:field-name "unchanged_as_path";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:attribute-unchanged/oc-netinst:state/oc-netinst:med {
      deviate add {
        sonic-ext:field-name "unchanged_med";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:attribute-unchanged/oc-netinst:state/oc-netinst:next-hop {
      deviate add {
        sonic-ext:field-name "unchanged_nexthop";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:filter-list/oc-netinst:config/oc-netinst:import-policy {
      deviate add {
        sonic-ext:field-name "filter_list_in";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:filter-list/oc-netinst:config/oc-netinst:export-policy {
      deviate add {
        sonic-ext:field-name "filter_list_out";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:filter-list/oc-netinst:state/oc-netinst:import-policy {
      deviate add {
        sonic-ext:field-name "filter_list_in";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:filter-list/oc-netinst:state/oc-netinst:export-policy {
      deviate add {
        sonic-ext:field-name "filter_list_out";
      }
    }


    deviation /oc-netinst:network-instances/oc-netinst:network-instance/oc-netinst:protocols/oc-netinst:protocol/oc-netinst:bgp/oc-netinst:neighbors/oc-netinst:neighbor/oc-netinst:afi-safis/oc-netinst:afi-safi/oc-netinst:next-hop-self/oc-netinst:config/oc-netinst:enabled {
      deviate add {
        sonic-ext:field-name "nhself";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:next-hop-self/oc-netinst:config/oc-netinst:force {
      deviate add {
        sonic-ext:field-name "nexthop_self_force";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:next-hop-self/oc-netinst:state/oc-netinst:enabled {
      deviate add {
        sonic-ext:field-name "nhself";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:next-hop-self/oc-netinst:state/oc-netinst:force {
      deviate add {
        sonic-ext:field-name "nexthop_self_force";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:prefix-list/oc-netinst:config/oc-netinst:import-policy {
      deviate add {
        sonic-ext:field-name "prefix_list_in";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:prefix-list/oc-netinst:config/oc-netinst:export-policy {
      deviate add {
        sonic-ext:field-name "prefix_list_out";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:prefix-list/oc-netinst:state/oc-netinst:import-policy {
      deviate add {
        sonic-ext:field-name "prefix_list_in";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:prefix-list/oc-netinst:state/oc-netinst:export-policy {
      deviate add {
        sonic-ext:field-name "prefix_list_out";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:remove-private-as/oc-netinst:config/oc-netinst:enabled {
      deviate add {
        sonic-ext:field-name "remove_private_as_enabled";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:remove-private-as/oc-netinst:config/oc-netinst:all {
      deviate add {
        sonic-ext:field-name "remove_private_as_all";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:remove-private-as/oc-netinst:config/oc-netinst:replace-as {
      deviate add {
        sonic-ext:field-name "replace_private_as";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:remove-private-as/oc-netinst:state/oc-netinst:enabled {
      deviate add {
        sonic-ext:field-name "remove_private_as_enabled";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:remove-private-as/oc-netinst:state/oc-netinst:all {
      deviate add {
        sonic-ext:field-name "remove_private_as_all";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:remove-private-as/oc-netinst:state/oc-netinst:replace-as {
      deviate add {
        sonic-ext:field-name "replace_private_as";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:capability-orf/oc-netinst:config/oc-netinst:orf-type {
      deviate add {
        sonic-ext:field-transformer "bgp_nbr_orf_type_fld_xfmr";
        sonic-ext:field-name "cap_orf";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:capability-orf/oc-netinst:state/oc-netinst:orf-type {
      deviate add {
        sonic-ext:field-transformer "bgp_nbr_orf_type_fld_xfmr";
        sonic-ext:field-name "cap_orf";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:allow-own-as/oc-netinst:config/oc-netinst:enabled {
      deviate add {
        sonic-ext:field-name "allow_as_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:allow-own-as/oc-netinst:config/oc-netinst:as-count {
      deviate add {
        sonic-ext:field-name "allow_as_count";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:allow-own-as/oc-netinst:config/oc-netinst:origin {
      deviate add {
        sonic-ext:field-name "allow_as_origin";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:allow-own-as/oc-netinst:state/oc-netinst:enabled {
      deviate add {
        sonic-ext:field-name "allow_as_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:allow-own-as/oc-netinst:state/oc-netinst:as-count {
      deviate add {
        sonic-ext:field-name "allow_as_count";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:allow-own-as/oc-netinst:state/oc-netinst:origin {
      deviate add {
        sonic-ext:field-name "allow_as_origin";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:attribute-unchanged/oc-netinst:config/oc-netinst:as-path {
      deviate add {
        sonic-ext:field-name "unchanged_as_path";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:attribute-unchanged/oc-netinst:config/oc-netinst:med {
      deviate add {
        sonic-ext:field-name "unchanged_med";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:attribute-unchanged/oc-netinst:config/oc-netinst:next-hop {
      deviate add {
        sonic-ext:field-name "unchanged_nexthop";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:attribute-unchanged/oc-netinst:state/oc-netinst:as-path {
      deviate add {
        sonic-ext:field-name "unchanged_as_path";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:attribute-unchanged/oc-netinst:state/oc-netinst:med {
      deviate add {
        sonic-ext:field-name "unchanged_med";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:attribute-unchanged/oc-netinst:state/oc-netinst:next-hop {
      deviate add {
        sonic-ext:field-name "unchanged_nexthop";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:filter-list/oc-netinst:config/oc-netinst:import-policy {
      deviate add {
        sonic-ext:field-name "filter_list_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:filter-list/oc-netinst:config/oc-netinst:export-policy {
      deviate add {
        sonic-ext:field-name "filter_list_out";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:filter-list/oc-netinst:state/oc-netinst:import-policy {
      deviate add {
        sonic-ext:field-name "filter_list_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:filter-list/oc-netinst:state/oc-netinst:export-policy {
      deviate add {
        sonic-ext:field-name "filter_list_out";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:next-hop-self/oc-netinst:config/oc-netinst:enabled {
      deviate add {
        sonic-ext:field-name "nhself";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:next-hop-self/oc-netinst:config/oc-netinst:force {
      deviate add {
        sonic-ext:field-name "nexthop_self_force";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:next-hop-self/oc-netinst:state/oc-netinst:enabled {
      deviate add {
        sonic-ext:field-name "nhself";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:next-hop-self/oc-netinst:state/oc-netinst:force {
      deviate add {
        sonic-ext:field-name "nexthop_self_force";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:prefix-list/oc-netinst:config/oc-netinst:import-policy {
      deviate add {
        sonic-ext:field-name "prefix_list_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:prefix-list/oc-netinst:config/oc-netinst:export-policy {
      deviate add {
        sonic-ext:field-name "prefix_list_out";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:prefix-list/oc-netinst:state/oc-netinst:import-policy {
      deviate add {
        sonic-ext:field-name "prefix_list_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:prefix-list/oc-netinst:state/oc-netinst:export-policy {
      deviate add {
        sonic-ext:field-name "prefix_list_out";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:remove-private-as/oc-netinst:config/oc-netinst:enabled {
      deviate add {
        sonic-ext:field-name "remove_private_as_enabled";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:remove-private-as/oc-netinst:config/oc-netinst:all {
      deviate add {
        sonic-ext:field-name "remove_private_as_all";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:remove-private-as/oc-netinst:config/oc-netinst:replace-as {
      deviate add {
        sonic-ext:field-name "replace_private_as";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:remove-private-as/oc-netinst:state/oc-netinst:enabled {
      deviate add {
        sonic-ext:field-name "remove_private_as_enabled";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:remove-private-as/oc-netinst:state/oc-netinst:all {
      deviate add {
        sonic-ext:field-name "remove_private_as_all";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:remove-private-as/oc-netinst:state/oc-netinst:replace-as {
      deviate add {
        sonic-ext:field-name "replace_private_as";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:capability-orf/oc-netinst:config/oc-netinst:orf-type {
      deviate add {
        sonic-ext:field-transformer "bgp_pgrp_orf_type_fld_xfmr";
        sonic-ext:field-name "cap_orf";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:capability-orf/oc-netinst:state/oc-netinst:orf-type {
      deviate add {
        sonic-ext:field-transformer "bgp_pgrp_orf_type_fld_xfmr";
        sonic-ext:field-name "cap_orf";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:config/oc-netinst:default-policy-name {
      deviate add {
        sonic-ext:field-name "default_rmap";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:state/oc-netinst:default-policy-name {
      deviate add {
        sonic-ext:field-name "default_rmap";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:config/oc-netinst:default-policy-name {
      deviate add {
        sonic-ext:field-name "default_rmap";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:state/oc-netinst:default-policy-name {
      deviate add {
        sonic-ext:field-name "default_rmap";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:config/oc-netinst:default-policy-name {
      deviate add {
        sonic-ext:field-name "default_rmap";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:state/oc-netinst:default-policy-name {
      deviate add {
        sonic-ext:field-name "default_rmap";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:config/oc-netinst:default-policy-name {
      deviate add {
        sonic-ext:field-name "default_rmap";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:state/oc-netinst:default-policy-name {
      deviate add {
        sonic-ext:field-name "default_rmap";
      }
    }
     deviation /oc-netinst:network-instances/oc-netinst:network-instance/oc-netinst:afts/oc-netinst:ipv4-unicast {
      deviate add {
        sonic-ext:subtree-transformer "ipv4_route_get_xfmr";
      }
     }

     deviation /oc-netinst:network-instances/oc-netinst:network-instance/oc-netinst:afts/oc-netinst:ipv6-unicast {
      deviate add {
        sonic-ext:subtree-transformer "ipv6_route_get_xfmr";
      }
     }

     deviation /oc-netinst:network-instances/oc-netinst:network-instance/oc-netinst:afts/oc-netinst:ipv4-multicast {
      deviate add {
        sonic-ext:subtree-transformer "ipv4_mroute_get_xfmr";
      }
     }

    deviation /oc-netinst:network-instances/oc-netinst:network-instance/oc-netinst:protocols/oc-netinst:protocol/oc-netinst-deviation:igmp-snooping {
			deviate add {
                sonic-ext:get-validate "igmp_snooping_validate_proto";
				sonic-ext:subtree-transformer "igmp_snooping_subtree_xfmr";
				sonic-ext:path-transformer "igmp_snooping_path_xfmr";
			}
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:route-advertise {
      deviate add {
        sonic-ext:table-name "NONE";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:route-advertise/oc-bgp-evpn-ext:route-advertise-list {
      deviate add {
        sonic-ext:table-name "BGP_GLOBALS_ROUTE_ADVERTISE";
        sonic-ext:key-transformer "bgp_advertise_route_key_xfmr";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:route-advertise/oc-bgp-evpn-ext:route-advertise-list/oc-bgp-evpn-ext:config/oc-bgp-evpn-ext:advertise-afi-safi {
      deviate add {
        sonic-ext:field-transformer "bgp_advertise_route_afi_safi_fld_xfmr";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:route-advertise/oc-bgp-evpn-ext:route-advertise-list/oc-bgp-evpn-ext:config/oc-bgp-evpn-ext:route-map {
      deviate add {
        sonic-ext:field-name "policy";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:route-advertise/oc-bgp-evpn-ext:route-advertise-list/oc-bgp-evpn-ext:state/oc-bgp-evpn-ext:advertise-afi-safi {
      deviate add {
        sonic-ext:field-transformer "bgp_advertise_route_afi_safi_fld_xfmr";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:route-advertise/oc-bgp-evpn-ext:route-advertise-list/oc-bgp-evpn-ext:state/oc-bgp-evpn-ext:route-map {
      deviate add {
        sonic-ext:field-name "policy";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:vnis/oc-bgp-evpn-ext:vni {
      deviate add {
        sonic-ext:key-transformer "bgp_evpn_vni_key_xfmr";
        sonic-ext:table-transformer "bgp_evpn_vni_tbl_xfmr";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:vnis/oc-bgp-evpn-ext:vni/oc-bgp-evpn-ext:config/oc-bgp-evpn-ext:vni-number {
      deviate add {
            sonic-ext:field-transformer "bgp_vni_number_fld_xfmr";
            sonic-ext:field-name "vni-number";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:config/oc-bgp-evpn-ext:advertise-all-vni {
      deviate add {
            sonic-ext:field-transformer "bgp_evpn_advertise_all_vni_fld_xfmr";
            sonic-ext:field-name "advertise-all-vni";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:config/oc-bgp-evpn-ext:advertise-pip {
      deviate add {
            sonic-ext:field-transformer "bgp_evpn_advertise_pip_enable_fld_xfmr";
            sonic-ext:subscribe-on-change "disable";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:config/oc-bgp-evpn-ext:advertise-pip-ip {
      deviate add {
            sonic-ext:field-transformer "bgp_evpn_advertise_pip_ip_fld_xfmr";
            sonic-ext:subscribe-on-change "disable";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:config/oc-bgp-evpn-ext:advertise-pip-peer-ip {
      deviate add {
            sonic-ext:field-transformer "bgp_evpn_advertise_pip_peer_ip_fld_xfmr";
            sonic-ext:subscribe-on-change "disable";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:default-originate/oc-bgp-evpn-ext:config/oc-bgp-evpn-ext:ipv4 {
      deviate add {
        sonic-ext:field-name "default-originate-ipv4";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:default-originate/oc-bgp-evpn-ext:config/oc-bgp-evpn-ext:ipv6 {
      deviate add {
        sonic-ext:field-name "default-originate-ipv6";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:default-originate/oc-bgp-evpn-ext:state/oc-bgp-evpn-ext:ipv4 {
      deviate add {
        sonic-ext:field-name "default-originate-ipv4";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:default-originate/oc-bgp-evpn-ext:state/oc-bgp-evpn-ext:ipv6 {
      deviate add {
        sonic-ext:field-name "default-originate-ipv6";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:dup-addr-detection/oc-bgp-evpn-ext:config/oc-bgp-evpn-ext:enabled {
      deviate add {
        sonic-ext:field-name "dad-enabled";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:dup-addr-detection/oc-bgp-evpn-ext:config/oc-bgp-evpn-ext:max-moves {
      deviate add {
        sonic-ext:field-name "dad-max-moves";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:dup-addr-detection/oc-bgp-evpn-ext:config/oc-bgp-evpn-ext:time {
      deviate add {
        sonic-ext:field-name "dad-time";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:dup-addr-detection/oc-bgp-evpn-ext:config/oc-bgp-evpn-ext:freeze {
      deviate add {
        sonic-ext:field-name "dad-freeze";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:dup-addr-detection/oc-bgp-evpn-ext:state/oc-bgp-evpn-ext:enabled {
      deviate add {
        sonic-ext:field-name "dad-enabled";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:dup-addr-detection/oc-bgp-evpn-ext:state/oc-bgp-evpn-ext:max-moves {
      deviate add {
        sonic-ext:field-name "dad-max-moves";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:dup-addr-detection/oc-bgp-evpn-ext:state/oc-bgp-evpn-ext:time {
      deviate add {
        sonic-ext:field-name "dad-time";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:dup-addr-detection/oc-bgp-evpn-ext:state/oc-bgp-evpn-ext:freeze {
      deviate add {
        sonic-ext:field-name "dad-freeze";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:vnis/oc-bgp-evpn-ext:vni/oc-bgp-evpn-ext:state {
      deviate add {
            sonic-ext:subtree-transformer "bgp_evpn_vni_state_xfmr";
            sonic-ext:subscribe-on-change "disable";
      }
    }


    deviation /oc-netinst:network-instances/oc-netinst:network-instance/oc-netinst-ext:global-sag {
      deviate add {
        sonic-ext:table-name "SAG_GLOBAL";
        sonic-ext:key-transformer "sag_global_key_xfmr";
      }
    }

    deviation /oc-netinst:network-instances/oc-netinst:network-instance/oc-netinst-ext:global-sag/oc-netinst-ext:config {
      deviate add {
      }
    }

    deviation /oc-netinst:network-instances/oc-netinst:network-instance/oc-netinst-ext:global-sag/oc-netinst-ext:config/oc-netinst-ext:anycast-mac {
      deviate add {
        sonic-ext:field-name "gwmac";
      }
    }

    deviation /oc-netinst:network-instances/oc-netinst:network-instance/oc-netinst-ext:global-sag/oc-netinst-ext:config/oc-netinst-ext:ipv4-enable {
      deviate add {
        sonic-ext:field-transformer "sag_ipv4_enable_xfmr";
      }
    }

    deviation /oc-netinst:network-instances/oc-netinst:network-instance/oc-netinst-ext:global-sag/oc-netinst-ext:config/oc-netinst-ext:ipv6-enable {
      deviate add {
        sonic-ext:field-transformer "sag_ipv6_enable_xfmr";
      }
    }

    deviation /oc-netinst:network-instances/oc-netinst:network-instance/oc-netinst-ext:global-sag/oc-netinst-ext:state {
      deviate add {
      }
    }

    deviation /oc-netinst:network-instances/oc-netinst:network-instance/oc-netinst-ext:global-sag/oc-netinst-ext:state/oc-netinst-ext:anycast-mac {
      deviate add {
        sonic-ext:field-name "gwmac";
      }
    }

    deviation /oc-netinst:network-instances/oc-netinst:network-instance/oc-netinst-ext:global-sag/oc-netinst-ext:state/oc-netinst-ext:ipv4-enable {
      deviate add {
        sonic-ext:field-transformer "sag_ipv4_enable_xfmr";
      }
    }

    deviation /oc-netinst:network-instances/oc-netinst:network-instance/oc-netinst-ext:global-sag/oc-netinst-ext:state/oc-netinst-ext:ipv6-enable {
      deviate add {
        sonic-ext:field-transformer "sag_ipv6_enable_xfmr";
      }
    }

    deviation /oc-netinst:network-instances/oc-netinst:network-instance/oc-vxlan:neighbour-suppress {
        deviate add {
            sonic-ext:table-name "SUPPRESS_VLAN_NEIGH";
            sonic-ext:key-transformer "vlan_nd_suppress_key_xfmr";
        }
    }

    deviation /oc-netinst:network-instances/oc-netinst:network-instance/oc-vxlan:neighbour-suppress/oc-vxlan:config/oc-vxlan:arp-and-nd-suppress {
        deviate add {
            sonic-ext:field-transformer "vlan_nd_suppress_fld_xfmr";
        }
    }

    deviation /oc-netinst:network-instances/oc-netinst:network-instance/oc-vxlan:neighbour-suppress/oc-vxlan:state/oc-vxlan:arp-and-nd-suppress {
        deviate add {
            sonic-ext:field-transformer "vlan_nd_suppress_fld_xfmr";
        }
    }

    deviation /oc-netinst:network-instances/oc-netinst:network-instance/oc-vxlan:vxlan-vni-instances {
        deviate add {
            sonic-ext:subtree-transformer "vxlan_vni_instance_subtree_xfmr";
        }
    }

  /*-------- NEXTHOP TRACKING --------*/

  deviation  "/oc-netinst:network-instances/oc-netinst:network-instance" +
             "/oc-nht-ext:nexthop-tracking/oc-nht-ext:address-family" {
    deviate add {
      sonic-ext:db-name "CONFIG_DB";
      sonic-ext:table-name "NHT_VRF_AF";
      sonic-ext:key-transformer "nht_vrf_af_tbl_key_xfmr";
    }
  }

  deviation  "/oc-netinst:network-instances/oc-netinst:network-instance" +
             "/oc-nht-ext:nexthop-tracking/oc-nht-ext:address-family" +
             "/oc-nht-ext:config/oc-nht-ext:family" {
    deviate add {
      sonic-ext:field-transformer  "nht_vrf_af_family_fld_xfmr";
    }
  }

  deviation  "/oc-netinst:network-instances/oc-netinst:network-instance" +
             "/oc-nht-ext:nexthop-tracking/oc-nht-ext:address-family" +
             "/oc-nht-ext:state/oc-nht-ext:family" {
    deviate add {
      sonic-ext:field-transformer  "nht_vrf_af_family_fld_xfmr";
    }
  }

  /*-------- OSPFV2_ROUTER --------*/

  deviation  "/oc-netinst:network-instances/oc-netinst:network-instance/oc-netinst:protocols" +
             "/oc-netinst:protocol/oc-netinst:ospfv2" {
    deviate add {
      sonic-ext:get-validate "ospfv2_validate_proto";
    }
  }

  deviation  "/oc-netinst:network-instances/oc-netinst:network-instance/oc-netinst:protocols" +
             "/oc-netinst:protocol/oc-netinst:ospfv2/oc-netinst:global" {
    deviate add {
      sonic-ext:db-name "CONFIG_DB";
      sonic-ext:table-name "OSPFV2_ROUTER";
      sonic-ext:key-transformer "ospfv2_router_tbl_key_xfmr";
    }
  }

  deviation "/oc-netinst:network-instances/oc-netinst:network-instance/oc-netinst:protocols" +
            "/oc-netinst:protocol/oc-netinst:ospfv2/oc-netinst:global" +
            "/oc-netinst:config/oc-ospfv2-ext:log-adjacency-state-changes" {
    deviate add {
      sonic-ext:field-name "log-adjacency-changes";
    }
  }
  
  deviation "/oc-netinst:network-instances/oc-netinst:network-instance/oc-netinst:protocols" +
            "/oc-netinst:protocol/oc-netinst:ospfv2/oc-netinst:global" +
            "/oc-netinst:config/oc-ospfv2-ext:opaque-lsa-capability" {
    deviate add {
      sonic-ext:field-name "opaque-lsa-capability";
    }
  }

  deviation "/oc-netinst:network-instances/oc-netinst:network-instance" +
            "/oc-netinst:protocols/oc-netinst:protocol/oc-netinst:ospfv2" +
            "/oc-netinst:global/oc-netinst:graceful-restart" +
            "/oc-netinst:config" +
            "/oc-netinst:enabled" {
    deviate add {
      sonic-ext:field-name "gr-enabled";
    }
  }

  deviation "/oc-netinst:network-instances/oc-netinst:network-instance" +
            "/oc-netinst:protocols/oc-netinst:protocol/oc-netinst:ospfv2" +
            "/oc-netinst:global/oc-netinst:graceful-restart" +
            "/oc-netinst:config" +
            "/oc-netinst:helper-only" {
    deviate add {
      sonic-ext:field-name "gr-helper-only";
    }
  }

  deviation "/oc-netinst:network-instances/oc-netinst:network-instance" +
            "/oc-netinst:protocols/oc-netinst:protocol/oc-netinst:ospfv2" +
            "/oc-netinst:global/oc-netinst:graceful-restart" +
            "/oc-netinst:config/oc-ospfv2-ext:grace-period" {
    deviate add {
      sonic-ext:field-name "gr-grace-period";
    }
  }

  deviation "/oc-netinst:network-instances/oc-netinst:network-instance" +
            "/oc-netinst:protocols/oc-netinst:protocol/oc-netinst:ospfv2" +
            "/oc-netinst:global/oc-netinst:graceful-restart" +
            "/oc-netinst:config/oc-ospfv2-ext:planned-only" {
    deviate add {
      sonic-ext:field-name "gr-helper-planned-only";
    }
  }

  deviation "/oc-netinst:network-instances/oc-netinst:network-instance" +
            "/oc-netinst:protocols/oc-netinst:protocol/oc-netinst:ospfv2" +
            "/oc-netinst:global/oc-netinst:graceful-restart" +
            "/oc-netinst:config/oc-ospfv2-ext:strict-lsa-checking" {
    deviate add {
      sonic-ext:field-name "gr-helper-strict-lsa-checking";
    }
  }

  deviation "/oc-netinst:network-instances/oc-netinst:network-instance" +
            "/oc-netinst:protocols/oc-netinst:protocol/oc-netinst:ospfv2" +
            "/oc-netinst:global/oc-netinst:graceful-restart" +
            "/oc-netinst:config/oc-ospfv2-ext:supported-grace-time" {
    deviate add {
      sonic-ext:field-name "gr-helper-supported-grace-time";
    }
  }
  
  deviation "/oc-netinst:network-instances/oc-netinst:network-instance" +
            "/oc-netinst:protocols/oc-netinst:protocol/oc-netinst:ospfv2" +
            "/oc-netinst:global/oc-netinst:graceful-restart" +
            "/oc-ospfv2-ext:helpers/oc-ospfv2-ext:helper" {
    deviate add {
      sonic-ext:db-name "CONFIG_DB";
      sonic-ext:table-name "OSPFV2_ROUTER_GR_NEIGHBOUR_HELPER";
      sonic-ext:key-transformer "ospfv2_router_gr_neighbor_helper_tbl_key_xfmr";
    }
  }

  deviation "/oc-netinst:network-instances/oc-netinst:network-instance" +
            "/oc-netinst:protocols/oc-netinst:protocol/oc-netinst:ospfv2" +
            "/oc-netinst:global/oc-netinst:graceful-restart" +
            "/oc-ospfv2-ext:helpers/oc-ospfv2-ext:helper" +
            "/oc-ospfv2-ext:config/oc-ospfv2-ext:neighbour-id" {
    deviate add {
      sonic-ext:field-transformer  "ospfv2_router_gr_neighbor_helper_neighbour_id_fld_xfmr";
    }
  }

  deviation "/oc-netinst:network-instances/oc-netinst:network-instance/oc-netinst:protocols" +
            "/oc-netinst:protocol/oc-netinst:ospfv2/oc-netinst:global/oc-netinst:timers" +
            "/oc-netinst:spf/oc-netinst:config" +
            "/oc-netinst:initial-delay" {
    deviate add {
      sonic-ext:field-name "spf-initial-delay";
    }
  }

  deviation "/oc-netinst:network-instances/oc-netinst:network-instance/oc-netinst:protocols" +
            "/oc-netinst:protocol/oc-netinst:ospfv2/oc-netinst:global/oc-netinst:timers" +
            "/oc-netinst:spf/oc-netinst:config" +
            "/oc-netinst:maximum-delay" {
    deviate add {
      sonic-ext:field-name "spf-maximum-delay";
    }
  }

  deviation "/oc-netinst:network-instances/oc-netinst:network-instance/oc-netinst:protocols" +
            "/oc-netinst:protocol/oc-netinst:ospfv2/oc-netinst:global/oc-netinst:timers" +
            "/oc-netinst:spf/oc-netinst:config" +
            "/oc-ospfv2-ext:throttle-delay" {
    deviate add {
      sonic-ext:field-name "spf-throttle-delay";
    }
  }


  deviation "/oc-netinst:network-instances/oc-netinst:network-instance" +
          "/oc-netinst:protocols/oc-netinst:protocol/oc-netinst:ospfv2" +
          "/oc-netinst:global/oc-netinst:timers/oc-netinst:lsa-generation" +
          "/oc-netinst:config/oc-ospfv2-ext:minimum-interval"  {
    deviate add {
      sonic-ext:field-name "lsa-min-interval-timer";
    }
  }

  deviation "/oc-netinst:network-instances/oc-netinst:network-instance" +
          "/oc-netinst:protocols/oc-netinst:protocol/oc-netinst:ospfv2" +
          "/oc-netinst:global/oc-netinst:timers/oc-netinst:lsa-generation" +
          "/oc-netinst:config/oc-ospfv2-ext:minimum-arrival"  {
    deviate add {
      sonic-ext:field-name "lsa-min-arrival-timer";
    }
  }

  deviation "/oc-netinst:network-instances/oc-netinst:network-instance/oc-netinst:protocols" +
            "/oc-netinst:protocol/oc-netinst:ospfv2/oc-netinst:global/oc-netinst:timers" +
            "/oc-netinst:lsa-generation/oc-netinst:config" +
            "/oc-ospfv2-ext:refresh-timer" {
    deviate add {
      sonic-ext:field-name "lsa-refresh-timer";
    }
  }

  deviation "/oc-netinst:network-instances/oc-netinst:network-instance/oc-netinst:protocols" +
            "/oc-netinst:protocol/oc-netinst:ospfv2/oc-netinst:global/oc-netinst:timers" +
            "/oc-netinst:max-metric/oc-netinst:config" +
            "/oc-ospfv2-ext:administrative" {
    deviate add {
      sonic-ext:field-name "max-metric-administrative";
    }
  }

  deviation "/oc-netinst:network-instances/oc-netinst:network-instance/oc-netinst:protocols" +
            "/oc-netinst:protocol/oc-netinst:ospfv2/oc-netinst:global/oc-netinst:timers" +
            "/oc-netinst:max-metric/oc-netinst:config" +
            "/oc-ospfv2-ext:on-startup" {
    deviate add {
      sonic-ext:field-name "max-metric-on-startup";
    }
  }

  deviation "/oc-netinst:network-instances/oc-netinst:network-instance/oc-netinst:protocols" +
            "/oc-netinst:protocol/oc-netinst:ospfv2/oc-netinst:global/oc-netinst:timers" +
            "/oc-netinst:max-metric/oc-netinst:config" +
            "/oc-ospfv2-ext:router-lsa-all" {
    deviate add {
      sonic-ext:field-name "max-metric-router-lsa-all";
    }
  }

  deviation "/oc-netinst:network-instances/oc-netinst:network-instance/oc-netinst:protocols" +
            "/oc-netinst:protocol/oc-netinst:ospfv2/oc-netinst:global/oc-netinst:timers" +
            "/oc-netinst:max-metric/oc-netinst:config" +
            "/oc-ospfv2-ext:router-lsa-stub" {
    deviate add {
      sonic-ext:field-name "max-metric-router-lsa-stub";
    }
  }

  deviation "/oc-netinst:network-instances/oc-netinst:network-instance/oc-netinst:protocols" +
            "/oc-netinst:protocol/oc-netinst:ospfv2/oc-netinst:global/oc-netinst:timers" +
            "/oc-netinst:max-metric/oc-netinst:config" +
            "/oc-ospfv2-ext:external-lsa-all" {
    deviate add {
      sonic-ext:field-name "max-metric-external-lsa-all";
    }
  }

  deviation "/oc-netinst:network-instances/oc-netinst:network-instance/oc-netinst:protocols" +
            "/oc-netinst:protocol/oc-netinst:ospfv2/oc-netinst:global/oc-netinst:timers" +
            "/oc-netinst:max-metric/oc-netinst:config" +
            "/oc-ospfv2-ext:external-lsa-connected" {
    deviate add {
      sonic-ext:field-name "max-metric-external-lsa-connected";
    }
  }

  /*
  deviation "/oc-netinst:network-instances/oc-netinst:network-instance/oc-netinst:protocols" +
            "/oc-netinst:protocol/oc-netinst:ospfv2/oc-netinst:global/oc-netinst:timers" +
            "/oc-netinst:max-metric/oc-netinst:config" +
            "/oc-ospfv2-ext:on-shutdown" {
    deviate add {
      sonic-ext:field-name "max-metric-on-shutdown";
    }
  }
  */

  deviation "/oc-netinst:network-instances/oc-netinst:network-instance/oc-netinst:protocols" +
            "/oc-netinst:protocol/oc-netinst:ospfv2/oc-netinst:global/oc-netinst:timers" +
            "/oc-netinst:max-metric/oc-netinst:state" +
            "/oc-ospfv2-ext:administrative" {
    deviate add {
      sonic-ext:field-name "max-metric-administrative";
    }
  }

  deviation "/oc-netinst:network-instances/oc-netinst:network-instance/oc-netinst:protocols" +
            "/oc-netinst:protocol/oc-netinst:ospfv2/oc-netinst:global/oc-netinst:timers" +
            "/oc-netinst:max-metric/oc-netinst:state" +
            "/oc-ospfv2-ext:on-startup" {
    deviate add {
      sonic-ext:field-name "max-metric-on-startup";
    }
  }

  deviation "/oc-netinst:network-instances/oc-netinst:network-instance/oc-netinst:protocols" +
            "/oc-netinst:protocol/oc-netinst:ospfv2/oc-netinst:global/oc-netinst:timers" +
            "/oc-netinst:max-metric/oc-netinst:state" +
            "/oc-ospfv2-ext:router-lsa-all" {
    deviate add {
      sonic-ext:field-name "max-metric-router-lsa-all";
    }
  }

  deviation "/oc-netinst:network-instances/oc-netinst:network-instance/oc-netinst:protocols" +
            "/oc-netinst:protocol/oc-netinst:ospfv2/oc-netinst:global/oc-netinst:timers" +
            "/oc-netinst:max-metric/oc-netinst:state" +
            "/oc-ospfv2-ext:router-lsa-stub" {
    deviate add {
      sonic-ext:field-name "max-metric-router-lsa-stub";
    }
  }

  deviation "/oc-netinst:network-instances/oc-netinst:network-instance/oc-netinst:protocols" +
            "/oc-netinst:protocol/oc-netinst:ospfv2/oc-netinst:global/oc-netinst:timers" +
            "/oc-netinst:max-metric/oc-netinst:state" +
            "/oc-ospfv2-ext:external-lsa-all" {
    deviate add {
      sonic-ext:field-name "max-metric-external-lsa-all";
    }
  }

  deviation "/oc-netinst:network-instances/oc-netinst:network-instance/oc-netinst:protocols" +
            "/oc-netinst:protocol/oc-netinst:ospfv2/oc-netinst:global/oc-netinst:timers" +
            "/oc-netinst:max-metric/oc-netinst:state" +
            "/oc-ospfv2-ext:external-lsa-connected" {
    deviate add {
      sonic-ext:field-name "max-metric-external-lsa-connected";
    }
  }

  deviation "/oc-netinst:network-instances/oc-netinst:network-instance/oc-netinst:protocols" +
            "/oc-netinst:protocol/oc-netinst:ospfv2/oc-netinst:global" +
            "/oc-ospfv2-ext:distance/oc-ospfv2-ext:config/oc-ospfv2-ext:all" {
    deviate add {
      sonic-ext:field-name "distance-all";
    }
  }

  deviation "/oc-netinst:network-instances/oc-netinst:network-instance/oc-netinst:protocols" +
            "/oc-netinst:protocol/oc-netinst:ospfv2/oc-netinst:global" +
            "/oc-ospfv2-ext:distance/oc-ospfv2-ext:config/oc-ospfv2-ext:intra-area" {
    deviate add {
      sonic-ext:field-name "distance-intra-area";
    }
  }

  deviation "/oc-netinst:network-instances/oc-netinst:network-instance/oc-netinst:protocols" +
            "/oc-netinst:protocol/oc-netinst:ospfv2/oc-netinst:global" +
            "/oc-ospfv2-ext:distance/oc-ospfv2-ext:config/oc-ospfv2-ext:inter-area" {
    deviate add {
      sonic-ext:field-name "distance-inter-area";
    }
  }

  deviation "/oc-netinst:network-instances/oc-netinst:network-instance/oc-netinst:protocols" +
            "/oc-netinst:protocol/oc-netinst:ospfv2/oc-netinst:global" +
            "/oc-ospfv2-ext:distance/oc-ospfv2-ext:config/oc-ospfv2-ext:external" {
    deviate add {
      sonic-ext:field-name "distance-external";
    }
  }


  /*-------- OSPFV2_ROUTER_DISTRIBUTE_ROUTE TABLE --------*/

  deviation  "/oc-netinst:network-instances/oc-netinst:network-instance/oc-netinst:protocols" +
             "/oc-netinst:protocol/oc-netinst:ospfv2/oc-netinst:global" +
             "/oc-ospfv2-ext:route-distribution-policies/oc-ospfv2-ext:distribute-list" {
    deviate add {
      sonic-ext:db-name "CONFIG_DB";
      sonic-ext:table-name "OSPFV2_ROUTER_DISTRIBUTE_ROUTE";
      sonic-ext:key-transformer "ospfv2_router_distribute_route_tbl_key_xfmr";
    }
  }

  /*
  deviation  "/oc-netinst:network-instances/oc-netinst:network-instance/oc-netinst:protocols" +
             "/oc-netinst:protocol/oc-netinst:ospfv2/oc-netinst:global" +
             "/oc-ospfv2-ext:route-distribution-policies/oc-ospfv2-ext:distribute-list" +
             "/oc-ospfv2-ext:config/oc-ospfv2-ext:access-list" {
    deviate add {
      sonic-ext:field-transformer  "ospfv2_router_distribute_route_access_list_fld_xfmr";
    }
  }

  deviation  "/oc-netinst:network-instances/oc-netinst:network-instance/oc-netinst:protocols" +
             "/oc-netinst:protocol/oc-netinst:ospfv2/oc-netinst:global" +
             "/oc-ospfv2-ext:route-distribution-policies/oc-ospfv2-ext:distribute-list" +
             "/oc-ospfv2-ext:state/oc-ospfv2-ext:access-list" {
    deviate add {
      sonic-ext:field-transformer  "ospfv2_router_distribute_route_access_list_fld_xfmr";
    }
  }
  */


  /*-------- OSPFV2_ROUTER_PASSIVE_INTERFACE TABLE --------*/

  deviation  "/oc-netinst:network-instances/oc-netinst:network-instance/oc-netinst:protocols" +
             "/oc-netinst:protocol/oc-netinst:ospfv2/oc-netinst:global" +
             "/oc-ospfv2-ext:passive-interfaces/oc-ospfv2-ext:passive-interface" {
    deviate add {
      sonic-ext:db-name "CONFIG_DB";
      sonic-ext:table-name "OSPFV2_ROUTER_PASSIVE_INTERFACE";
      sonic-ext:key-transformer "ospfv2_router_passive_interface_tbl_key_xfmr";
    }
  }

  deviation  "/oc-netinst:network-instances/oc-netinst:network-instance/oc-netinst:protocols" +
             "/oc-netinst:protocol/oc-netinst:ospfv2/oc-netinst:global" +
             "/oc-ospfv2-ext:passive-interfaces/oc-ospfv2-ext:passive-interface" +
             "/oc-ospfv2-ext:config/oc-ospfv2-ext:name" {
    deviate add {
      sonic-ext:field-transformer  "ospfv2_router_passive_interface_name_fld_xfmr";
    }
  }

  deviation  "/oc-netinst:network-instances/oc-netinst:network-instance/oc-netinst:protocols" +
             "/oc-netinst:protocol/oc-netinst:ospfv2/oc-netinst:global" +
             "/oc-ospfv2-ext:passive-interfaces/oc-ospfv2-ext:passive-interface" +
             "/oc-ospfv2-ext:state/oc-ospfv2-ext:name" {
    deviate add {
      sonic-ext:field-transformer  "ospfv2_router_passive_interface_name_fld_xfmr";
    }
  }

  deviation  "/oc-netinst:network-instances/oc-netinst:network-instance/oc-netinst:protocols" +
             "/oc-netinst:protocol/oc-netinst:ospfv2/oc-netinst:global" +
             "/oc-ospfv2-ext:passive-interfaces/oc-ospfv2-ext:passive-interface" +
             "/oc-ospfv2-ext:config/oc-ospfv2-ext:subinterface" {
    deviate add {
      sonic-ext:field-transformer  "ospfv2_router_passive_interface_subinterface_fld_xfmr";
    }
  }

  deviation  "/oc-netinst:network-instances/oc-netinst:network-instance/oc-netinst:protocols" +
             "/oc-netinst:protocol/oc-netinst:ospfv2/oc-netinst:global" +
             "/oc-ospfv2-ext:passive-interfaces/oc-ospfv2-ext:passive-interface" +
             "/oc-ospfv2-ext:state/oc-ospfv2-ext:subinterface" {
    deviate add {
      sonic-ext:field-transformer  "ospfv2_router_passive_interface_subinterface_fld_xfmr";
    }
  }

  deviation  "/oc-netinst:network-instances/oc-netinst:network-instance/oc-netinst:protocols" +
             "/oc-netinst:protocol/oc-netinst:ospfv2/oc-netinst:global" +
             "/oc-ospfv2-ext:passive-interfaces/oc-ospfv2-ext:passive-interface" +
             "/oc-ospfv2-ext:config/oc-ospfv2-ext:address" {
    deviate add {
      sonic-ext:field-transformer  "ospfv2_router_passive_interface_address_fld_xfmr";
    }
  }

  deviation  "/oc-netinst:network-instances/oc-netinst:network-instance/oc-netinst:protocols" +
             "/oc-netinst:protocol/oc-netinst:ospfv2/oc-netinst:global" +
             "/oc-ospfv2-ext:passive-interfaces/oc-ospfv2-ext:passive-interface" +
             "/oc-ospfv2-ext:state/oc-ospfv2-ext:address" {
    deviate add {
      sonic-ext:field-transformer  "ospfv2_router_passive_interface_address_fld_xfmr";
    }
  }

  /*-------- OSPFV2_ROUTER_AREA --------*/

  deviation  "/oc-netinst:network-instances/oc-netinst:network-instance/oc-netinst:protocols" +
             "/oc-netinst:protocol/oc-netinst:ospfv2/oc-netinst:areas/oc-netinst:area"  {
    deviate add {
      sonic-ext:db-name "CONFIG_DB";
      sonic-ext:table-name "OSPFV2_ROUTER_AREA";
      sonic-ext:table-transformer "ospfv2_router_area_tbl_xfmr";
      sonic-ext:key-transformer "ospfv2_router_area_tbl_key_xfmr";
    }
  }

  deviation "/oc-netinst:network-instances/oc-netinst:network-instance/oc-netinst:protocols" +
            "/oc-netinst:protocol/oc-netinst:ospfv2/oc-netinst:areas/oc-netinst:area" +
            "/oc-netinst:config/oc-netinst:identifier" {
    deviate add {
      sonic-ext:field-transformer  "ospfv2_router_area_area_id_fld_xfmr";
    }
  }

  deviation "/oc-netinst:network-instances/oc-netinst:network-instance/oc-netinst:protocols" +
            "/oc-netinst:protocol/oc-netinst:ospfv2/oc-netinst:areas/oc-netinst:area" +
            "/oc-netinst:config/oc-ospfv2-ext:authentication-type" {
    deviate add {
      sonic-ext:field-name "authentication";
    }
  }

  deviation "/oc-netinst:network-instances/oc-netinst:network-instance/oc-netinst:protocols" +
            "/oc-netinst:protocol/oc-netinst:ospfv2/oc-netinst:areas/oc-netinst:area" +
            "/oc-ospfv2-ext:stub/oc-ospfv2-ext:config/oc-ospfv2-ext:enable" {
    deviate add {
      sonic-ext:field-name "stub";
    }
  }

  deviation "/oc-netinst:network-instances/oc-netinst:network-instance/oc-netinst:protocols" +
            "/oc-netinst:protocol/oc-netinst:ospfv2/oc-netinst:areas/oc-netinst:area" +
            "/oc-ospfv2-ext:stub/oc-ospfv2-ext:config/oc-ospfv2-ext:no-summary" {
    deviate add {
      sonic-ext:field-name "stub-no-summary";
    }
  }

  deviation "/oc-netinst:network-instances/oc-netinst:network-instance/oc-netinst:protocols" +
            "/oc-netinst:protocol/oc-netinst:ospfv2/oc-netinst:areas/oc-netinst:area" +
            "/oc-ospfv2-ext:stub/oc-ospfv2-ext:config/oc-ospfv2-ext:default-cost" {
    deviate add {
      sonic-ext:field-name "stub-default-cost";
    }
  }

  /*
  deviation  "/oc-netinst:network-instances/oc-netinst:network-instance/oc-netinst:protocols" +
             "/oc-netinst:protocol/oc-netinst:ospfv2/oc-netinst:global" +
             "/oc-netinst:inter-area-propagation-policies" +
             "/oc-ospfv2-ext:inter-area-policy/oc-ospfv2-ext:import-list"  +
             "/oc-ospfv2-ext:config/oc-ospfv2-ext:name" {
    deviate add {
      sonic-ext:field-transformer "ospfv2_router_area_policy_import_list_fld_xfmr";
    }
  }

  deviation  "/oc-netinst:network-instances/oc-netinst:network-instance/oc-netinst:protocols" +
             "/oc-netinst:protocol/oc-netinst:ospfv2/oc-netinst:global" +
             "/oc-netinst:inter-area-propagation-policies" +
             "/oc-ospfv2-ext:inter-area-policy/oc-ospfv2-ext:import-list"  +
             "/oc-ospfv2-ext:state/oc-ospfv2-ext:name" {
    deviate add {
      sonic-ext:field-transformer "ospfv2_router_area_policy_import_list_fld_xfmr";
    }
  }

  deviation  "/oc-netinst:network-instances/oc-netinst:network-instance/oc-netinst:protocols" +
             "/oc-netinst:protocol/oc-netinst:ospfv2/oc-netinst:global" +
             "/oc-netinst:inter-area-propagation-policies" +
             "/oc-ospfv2-ext:inter-area-policy/oc-ospfv2-ext:export-list"  +
             "/oc-ospfv2-ext:config/oc-ospfv2-ext:name" {
    deviate add {
      sonic-ext:field-transformer "ospfv2_router_area_policy_export_list_fld_xfmr";
    }
  }

  deviation  "/oc-netinst:network-instances/oc-netinst:network-instance/oc-netinst:protocols" +
             "/oc-netinst:protocol/oc-netinst:ospfv2/oc-netinst:global" +
             "/oc-netinst:inter-area-propagation-policies" +
             "/oc-ospfv2-ext:inter-area-policy/oc-ospfv2-ext:export-list"  +
             "/oc-ospfv2-ext:state/oc-ospfv2-ext:name" {
    deviate add {
      sonic-ext:field-transformer "ospfv2_router_area_policy_export_list_fld_xfmr";
    }
  }
  */

  deviation  "/oc-netinst:network-instances/oc-netinst:network-instance/oc-netinst:protocols" +
             "/oc-netinst:protocol/oc-netinst:ospfv2/oc-netinst:global" +
             "/oc-netinst:inter-area-propagation-policies" +
             "/oc-ospfv2-ext:inter-area-policy/oc-ospfv2-ext:filter-list-in"  +
             "/oc-ospfv2-ext:config/oc-ospfv2-ext:name" {
    deviate add {
      sonic-ext:field-name "filter-list-in";
    }
  }

  deviation  "/oc-netinst:network-instances/oc-netinst:network-instance/oc-netinst:protocols" +
             "/oc-netinst:protocol/oc-netinst:ospfv2/oc-netinst:global" +
             "/oc-netinst:inter-area-propagation-policies" +
             "/oc-ospfv2-ext:inter-area-policy/oc-ospfv2-ext:filter-list-in"  +
             "/oc-ospfv2-ext:state/oc-ospfv2-ext:name" {
    deviate add {
      sonic-ext:field-name "filter-list-in";
    }
  }

  deviation  "/oc-netinst:network-instances/oc-netinst:network-instance/oc-netinst:protocols" +
             "/oc-netinst:protocol/oc-netinst:ospfv2/oc-netinst:global" +
             "/oc-netinst:inter-area-propagation-policies" +
             "/oc-ospfv2-ext:inter-area-policy/oc-ospfv2-ext:filter-list-out"  +
             "/oc-ospfv2-ext:config/oc-ospfv2-ext:name" {
    deviate add {
      sonic-ext:field-name "filter-list-out";
    }
  }

  deviation  "/oc-netinst:network-instances/oc-netinst:network-instance/oc-netinst:protocols" +
             "/oc-netinst:protocol/oc-netinst:ospfv2/oc-netinst:global" +
             "/oc-netinst:inter-area-propagation-policies" +
             "/oc-ospfv2-ext:inter-area-policy/oc-ospfv2-ext:filter-list-out"  +
             "/oc-ospfv2-ext:state/oc-ospfv2-ext:name" {
    deviate add {
      sonic-ext:field-name "filter-list-out";
    }
  }

  /*-------- OSPFV2_ROUTER_AREA_VIRTUAL_LINK --------*/

  deviation  "/oc-netinst:network-instances/oc-netinst:network-instance/oc-netinst:protocols" +
             "/oc-netinst:protocol/oc-netinst:ospfv2/oc-netinst:areas/oc-netinst:area" +
             "/oc-netinst:virtual-links/oc-netinst:virtual-link"  {
    deviate add {
      sonic-ext:db-name "CONFIG_DB";
      sonic-ext:table-name "OSPFV2_ROUTER_AREA_VIRTUAL_LINK";
      sonic-ext:key-transformer "ospfv2_router_area_virtual_link_tbl_key_xfmr";
    }
  }

  deviation  "/oc-netinst:network-instances/oc-netinst:network-instance/oc-netinst:protocols" +
             "/oc-netinst:protocol/oc-netinst:ospfv2/oc-netinst:areas/oc-netinst:area" +
             "/oc-netinst:virtual-links/oc-netinst:virtual-link" +
             "/oc-netinst:config/oc-netinst:remote-router-id" {
    deviate add {
      sonic-ext:field-transformer  "ospfv2_router_area_vl_remote_router_id_fld_xfmr";
    }
  }

  deviation  "/oc-netinst:network-instances/oc-netinst:network-instance/oc-netinst:protocols" +
             "/oc-netinst:protocol/oc-netinst:ospfv2/oc-netinst:areas/oc-netinst:area" +
             "/oc-netinst:virtual-links/oc-netinst:virtual-link" +
             "/oc-netinst:config/oc-ospfv2-ext:authentication-key" {
    deviate add {
      sonic-ext:field-transformer  "ospfv2_router_area_vl_authentication_key_fld_xfmr";
    }
  }

  deviation  "/oc-netinst:network-instances/oc-netinst:network-instance/oc-netinst:protocols" +
             "/oc-netinst:protocol/oc-netinst:ospfv2/oc-netinst:areas/oc-netinst:area" +
             "/oc-netinst:virtual-links/oc-netinst:virtual-link" +
             "/oc-netinst:config/oc-ospfv2-ext:authentication-key-encrypted" {
    deviate add {
      sonic-ext:field-transformer  "ospfv2_router_area_vl_authentication_key_encr_fld_xfmr";
    }
  }

  deviation  "/oc-netinst:network-instances/oc-netinst:network-instance/oc-netinst:protocols" +
             "/oc-netinst:protocol/oc-netinst:ospfv2/oc-netinst:areas/oc-netinst:area" +
             "/oc-netinst:virtual-links/oc-netinst:virtual-link" +
             "/oc-ospfv2-ext:md-authentications/oc-ospfv2-ext:md-authentication" {
    deviate add {
      sonic-ext:db-name "CONFIG_DB";
      sonic-ext:table-name "OSPFV2_ROUTER_AREA_VLMD_AUTHENTICATION";
      sonic-ext:key-transformer "ospfv2_router_area_vlmd_auth_tbl_key_xfmr";
    }
  }

  deviation  "/oc-netinst:network-instances/oc-netinst:network-instance/oc-netinst:protocols" +
             "/oc-netinst:protocol/oc-netinst:ospfv2/oc-netinst:areas/oc-netinst:area" +
             "/oc-netinst:virtual-links/oc-netinst:virtual-link" +
             "/oc-ospfv2-ext:md-authentications/oc-ospfv2-ext:md-authentication" +
             "/oc-ospfv2-ext:config/oc-ospfv2-ext:authentication-key-id" {
    deviate add {
      sonic-ext:field-transformer  "ospfv2_router_area_vlmd_auth_key_id_fld_xfmr";
    }
  }

  deviation  "/oc-netinst:network-instances/oc-netinst:network-instance/oc-netinst:protocols" +
             "/oc-netinst:protocol/oc-netinst:ospfv2/oc-netinst:areas/oc-netinst:area" +
             "/oc-netinst:virtual-links/oc-netinst:virtual-link" +
             "/oc-ospfv2-ext:md-authentications/oc-ospfv2-ext:md-authentication" +
             "/oc-ospfv2-ext:config/oc-ospfv2-ext:authentication-md5-key" {
    deviate add {
      sonic-ext:field-transformer  "ospfv2_router_area_vlmd_auth_md5_key_fld_xfmr";
    }
  }

  deviation  "/oc-netinst:network-instances/oc-netinst:network-instance/oc-netinst:protocols" +
             "/oc-netinst:protocol/oc-netinst:ospfv2/oc-netinst:areas/oc-netinst:area" +
             "/oc-netinst:virtual-links/oc-netinst:virtual-link" +
             "/oc-ospfv2-ext:md-authentications/oc-ospfv2-ext:md-authentication" +
             "/oc-ospfv2-ext:config/oc-ospfv2-ext:authentication-key-encrypted" {
    deviate add {
      sonic-ext:field-transformer  "ospfv2_router_area_vlmd_auth_key_encr_fld_xfmr";
    }
  }
  /*-------- OSPFV2_ROUTER_AREA_NETWORK --------*/

  deviation  "/oc-netinst:network-instances/oc-netinst:network-instance/oc-netinst:protocols" +
             "/oc-netinst:protocol/oc-netinst:ospfv2/oc-netinst:areas/oc-netinst:area" +
             "/oc-ospfv2-ext:networks/oc-ospfv2-ext:network"  {
    deviate add {
      sonic-ext:db-name "CONFIG_DB";
      sonic-ext:table-name "OSPFV2_ROUTER_AREA_NETWORK";
      sonic-ext:key-transformer "ospfv2_router_area_network_tbl_key_xfmr";
    }
  }

  deviation "/oc-netinst:network-instances/oc-netinst:network-instance/oc-netinst:protocols" +
            "/oc-netinst:protocol/oc-netinst:ospfv2/oc-netinst:areas/oc-netinst:area" +
            "/oc-ospfv2-ext:networks/oc-ospfv2-ext:network/oc-ospfv2-ext:config" +
            "/oc-ospfv2-ext:address-prefix" {
    deviate add {
      sonic-ext:field-transformer  "ospfv2_router_network_prefix_fld_xfmr";
    }
  }

  deviation "/oc-netinst:network-instances/oc-netinst:network-instance/oc-netinst:protocols" +
            "/oc-netinst:protocol/oc-netinst:ospfv2/oc-netinst:areas/oc-netinst:area" +
            "/oc-ospfv2-ext:networks/oc-ospfv2-ext:network/oc-ospfv2-ext:state" +
            "/oc-ospfv2-ext:address-prefix" {
    deviate add {
      sonic-ext:field-transformer  "ospfv2_router_network_prefix_fld_xfmr";
    }
  }
  /*-------- OSPFV2_ROUTER_AREA_POLICY_ADDRESS_RANGE --------*/

  deviation  "/oc-netinst:network-instances/oc-netinst:network-instance/oc-netinst:protocols" +
             "/oc-netinst:protocol/oc-netinst:ospfv2/oc-netinst:global" +
             "/oc-netinst:inter-area-propagation-policies" +
             "/oc-ospfv2-ext:inter-area-policy"  {
    deviate add {
      sonic-ext:db-name "CONFIG_DB";
      sonic-ext:table-name "OSPFV2_ROUTER_AREA";
      sonic-ext:key-transformer "ospfv2_router_area_policy_tbl_key_xfmr";
    }
  }

  deviation  "/oc-netinst:network-instances/oc-netinst:network-instance/oc-netinst:protocols" +
             "/oc-netinst:protocol/oc-netinst:ospfv2/oc-netinst:global" +
             "/oc-netinst:inter-area-propagation-policies" +
             "/oc-ospfv2-ext:inter-area-policy"  +
             "/oc-ospfv2-ext:config/oc-ospfv2-ext:src-area" {
    deviate add {
      sonic-ext:field-transformer  "ospfv2_router_area_policy_src_area_fld_xfmr";
    }
  }

  deviation  "/oc-netinst:network-instances/oc-netinst:network-instance/oc-netinst:protocols" +
             "/oc-netinst:protocol/oc-netinst:ospfv2/oc-netinst:global" +
             "/oc-netinst:inter-area-propagation-policies" +
             "/oc-ospfv2-ext:inter-area-policy"  +
             "/oc-ospfv2-ext:state/oc-ospfv2-ext:src-area" {
    deviate add {
      sonic-ext:field-transformer  "ospfv2_router_area_policy_src_area_fld_xfmr";
    }
  }

  deviation  "/oc-netinst:network-instances/oc-netinst:network-instance/oc-netinst:protocols" +
             "/oc-netinst:protocol/oc-netinst:ospfv2/oc-netinst:global" +
             "/oc-netinst:inter-area-propagation-policies/oc-ospfv2-ext:inter-area-policy" +
             "/oc-ospfv2-ext:ranges/oc-ospfv2-ext:range" {
    deviate add {
      sonic-ext:db-name "CONFIG_DB";
      sonic-ext:table-name "OSPFV2_ROUTER_AREA_POLICY_ADDRESS_RANGE";
      sonic-ext:key-transformer "ospfv2_router_area_policy_address_range_tbl_key_xfmr";
    }
  }

  /*-------- OSPFV2_INTERFACE placed in /oc-intf:interfaces/oc-intf:interface ---------- */



  /*----------------OSPFV2_ROUTER SHOW COMMANDS-------------------------*/
  deviation  "/oc-netinst:network-instances/oc-netinst:network-instance/oc-netinst:protocols" +
             "/oc-netinst:protocol/oc-netinst:ospfv2/oc-netinst:global/oc-netinst:state" {
    deviate add {
      sonic-ext:subtree-transformer "ospfv2_global_state_xfmr";
    }
  }
  deviation "/oc-netinst:network-instances/oc-netinst:network-instance" +
            "/oc-netinst:protocols/oc-netinst:protocol/oc-netinst:ospfv2" +
            "/oc-netinst:global/oc-ospfv2-ext:distance" +
            "/oc-ospfv2-ext:state" {
    deviate add {
      sonic-ext:subtree-transformer "ospfv2_global_distance_state_xfmr";
    }
  }
  deviation "/oc-netinst:network-instances/oc-netinst:network-instance" +
            "/oc-netinst:protocols/oc-netinst:protocol/oc-netinst:ospfv2" +
            "/oc-netinst:global/oc-netinst:graceful-restart" +
            "/oc-netinst:state" {
    deviate add {
      sonic-ext:subtree-transformer "ospfv2_global_graceful_restart_state_xfmr";
    }
  }
  deviation  "/oc-netinst:network-instances/oc-netinst:network-instance/oc-netinst:protocols" +
             "/oc-netinst:protocol/oc-netinst:ospfv2/oc-netinst:global/oc-netinst:timers/oc-netinst:spf/oc-netinst:state" {
    deviate add {
      sonic-ext:subtree-transformer "ospfv2_global_timers_spf_state_xfmr";
    }
  }
  deviation  "/oc-netinst:network-instances/oc-netinst:network-instance/oc-netinst:protocols" +
             "/oc-netinst:protocol/oc-netinst:ospfv2/oc-netinst:global/oc-netinst:timers/oc-netinst:lsa-generation/oc-netinst:state" {
    deviate add {
      sonic-ext:subtree-transformer "ospfv2_global_timers_lsa_generation_state_xfmr";
    }
  }
  deviation  "/oc-netinst:network-instances/oc-netinst:network-instance/oc-netinst:protocols" +
             "/oc-netinst:protocol/oc-netinst:ospfv2/oc-netinst:areas/oc-netinst:area/oc-netinst:state" {
    deviate add {
      sonic-ext:subtree-transformer "ospfv2_areas_area_state_xfmr";
    }
  }
  deviation  "/oc-netinst:network-instances/oc-netinst:network-instance/oc-netinst:protocols" +
             "/oc-netinst:protocol/oc-netinst:ospfv2/oc-netinst:areas/oc-netinst:area/oc-netinst:interfaces" {
    deviate add {
      sonic-ext:subtree-transformer "ospfv2_neighbors_state_xfmr";
    }
  }
  deviation  "/oc-netinst:network-instances/oc-netinst:network-instance/oc-netinst:protocols" +
             "/oc-netinst:protocol/oc-netinst:ospfv2/oc-ospfv2-ext:route-tables" {
    deviate add {
      sonic-ext:subtree-transformer "ospfv2_route_table_xfmr";
    }
  }
  deviation "/oc-netinst:network-instances/oc-netinst:network-instance/oc-netinst:protocols" +
            "/oc-netinst:protocol/oc-netinst:ospfv2/oc-netinst:areas/oc-netinst:area/oc-ospfv2-ext:stub/oc-ospfv2-ext:state" {
    deviate add {
      sonic-ext:subtree-transformer "ospfv2_stub_state_xfmr";
    }
  }
  deviation "/oc-netinst:network-instances/oc-netinst:network-instance/oc-netinst:protocols" +
            "/oc-netinst:protocol/oc-netinst:ospfv2/oc-netinst:areas/oc-netinst:area/oc-netinst:lsdb" {
    deviate add {
      sonic-ext:subtree-transformer "ospfv2_lsdb_state_xfmr";
    }
  }
  deviation  "/oc-netinst:network-instances/oc-netinst:network-instance/oc-netinst:protocols" +
             "/oc-netinst:protocol/oc-netinst:ospfv2/oc-netinst:areas/oc-netinst:area/oc-netinst:virtual-links/oc-netinst:virtual-link/oc-netinst:state" {
    deviate add {
      sonic-ext:subtree-transformer "ospfv2_vlink_state_xfmr";
    }
  }
  deviation  "/oc-netinst:network-instances/oc-netinst:network-instance/oc-netinst:protocols" +
             "/oc-netinst:protocol/oc-netinst:ospfv2/oc-netinst:areas/oc-netinst:area/oc-netinst:virtual-links/oc-netinst:virtual-link/oc-ospfv2-ext:message-statistics" {
    deviate add {
      sonic-ext:subtree-transformer "ospfv2_vlink_message_statistics_xfmr";
    }
  }
  deviation  "/oc-netinst:network-instances/oc-netinst:network-instance/oc-netinst:protocols" +
             "/oc-netinst:protocol/oc-netinst:ospfv2/oc-netinst:areas/oc-netinst:area/oc-netinst:virtual-links/oc-netinst:virtual-link/oc-ospfv2-ext:neighbours/oc-ospfv2-ext:neighbour" {
    deviate add {
      sonic-ext:subtree-transformer "ospfv2_vlink_neighbor_state_xfmr";
    }
  }

  deviation "/oc-netinst:network-instances/oc-netinst:network-instance/oc-netinst:protocols/oc-netinst:protocol/oc-netinst:igmp" {
     deviate add {
       sonic-ext:get-validate "igmp_validate_proto";
     }
  }
  
  deviation "/oc-netinst:network-instances/oc-netinst:network-instance/oc-netinst:protocols/oc-netinst:protocol/oc-netinst:igmp/oc-igmp-ext:groups" {
     deviate add {
       sonic-ext:subtree-transformer "igmp_groups_get_xfmr";
     }
  }

  deviation "/oc-netinst:network-instances/oc-netinst:network-instance/oc-netinst:protocols/oc-netinst:protocol/oc-netinst:igmp/oc-igmp-ext:statistics" {
     deviate add {
       sonic-ext:subtree-transformer "igmp_stats_get_xfmr";
     }
  }

  deviation "/oc-netinst:network-instances/oc-netinst:network-instance/oc-netinst:protocols/oc-netinst:protocol/oc-netinst:igmp/oc-netinst:interfaces/oc-netinst:interface/oc-netinst:counters" {
     deviate add {
       sonic-ext:subtree-transformer "igmp_intf_stats_get_xfmr";
     }
  }

  deviation "/oc-netinst:network-instances/oc-netinst:network-instance/oc-netinst:protocols/oc-netinst:protocol/oc-netinst:igmp/oc-netinst:interfaces" {
     deviate add {
       sonic-ext:subtree-transformer "igmp_interface_get_xfmr";
       sonic-ext:table-name "NONE";
     }
  }

  deviation "/oc-netinst:network-instances/oc-netinst:network-instance/oc-netinst:protocols/oc-netinst:protocol/oc-netinst:igmp/oc-igmp-ext:sources" {
     deviate add {
       sonic-ext:subtree-transformer "igmp_sources_get_xfmr";
     }
  }

  deviation  "/oc-netinst:network-instances/oc-netinst:network-instance/oc-netinst:protocols" +
             "/oc-netinst:protocol/oc-netinst:pim" {
    deviate add {
      sonic-ext:get-validate "pim_validate_proto";
    }
  }

  deviation /oc-netinst:network-instances/oc-netinst:network-instance/oc-netinst:protocols/oc-netinst:protocol/oc-netinst:pim/oc-netinst:global {
      deviate add {
          sonic-ext:db-name "CONFIG_DB";
          sonic-ext:table-name "PIM_GLOBALS";
          sonic-ext:key-transformer "pim_gbl_tbl_key_xfmr";
      }
  }

  deviation /oc-netinst:network-instances/oc-netinst:network-instance/oc-netinst:protocols/oc-netinst:protocol/oc-netinst:pim/oc-netinst:global/oc-netinst:config/oc-netinst:join-prune-interval {
      deviate add {
          sonic-ext:field-name "join-prune-interval";
      }
  }

  deviation /oc-netinst:network-instances/oc-netinst:network-instance/oc-netinst:protocols/oc-netinst:protocol/oc-netinst:pim/oc-netinst:global/oc-netinst:state {
      deviate add {
          sonic-ext:subscribe-on-change "disable";
      }
  }

  deviation /oc-netinst:network-instances/oc-netinst:network-instance/oc-netinst:protocols/oc-netinst:protocol/oc-netinst:pim/oc-netinst:global/oc-netinst:ssm/oc-netinst:state {
      deviate add {
          sonic-ext:subscribe-on-change "disable";
      }
  }

  deviation /oc-netinst:network-instances/oc-netinst:network-instance/oc-netinst:protocols/oc-netinst:protocol/oc-netinst:pim/oc-netinst:global/oc-netinst:config/oc-netinst:keep-alive-timer {
      deviate add {
          sonic-ext:field-name "keep-alive-timer";
      }
  }

  deviation /oc-netinst:network-instances/oc-netinst:network-instance/oc-netinst:protocols/oc-netinst:protocol/oc-netinst:pim/oc-netinst:global/oc-netinst:config/oc-netinst:ecmp-enabled {
      deviate add {
          sonic-ext:field-name "ecmp-enabled";
      }
  }

  deviation /oc-netinst:network-instances/oc-netinst:network-instance/oc-netinst:protocols/oc-netinst:protocol/oc-netinst:pim/oc-netinst:global/oc-netinst:config/oc-netinst:ecmp-rebalance-enabled {
      deviate add {
          sonic-ext:field-name "ecmp-rebalance-enabled";
      }
  }

  deviation /oc-netinst:network-instances/oc-netinst:network-instance/oc-netinst:protocols/oc-netinst:protocol/oc-netinst:pim/oc-netinst:global/oc-netinst:tib {
      deviate add {
          sonic-ext:subtree-transformer "pim_tib_state_xfmr";
          sonic-ext:subscribe-on-change "disable";
      }
  }

  deviation /oc-netinst:network-instances/oc-netinst:network-instance/oc-netinst:protocols/oc-netinst:protocol/oc-netinst:pim/oc-netinst:interfaces/oc-netinst:interface {
      deviate add {
          sonic-ext:db-name "CONFIG_DB";
          sonic-ext:table-name "PIM_INTERFACE";
          sonic-ext:key-transformer "pim_intf_tbl_key_xfmr";
      }
  }

  deviation /oc-netinst:network-instances/oc-netinst:network-instance/oc-netinst:protocols/oc-netinst:protocol/oc-netinst:pim/oc-netinst:interfaces/oc-netinst:interface/oc-netinst:config/oc-netinst:interface-id {
      deviate add {
          sonic-ext:field-transformer "pim_intf_id_fld_xfmr";
      }
  }

  deviation /oc-netinst:network-instances/oc-netinst:network-instance/oc-netinst:protocols/oc-netinst:protocol/oc-netinst:pim/oc-netinst:interfaces/oc-netinst:interface/oc-netinst:config/oc-netinst:mode {
      deviate add {
          sonic-ext:field-transformer "pim_intf_mode_fld_xfmr";
      }
  }

  deviation /oc-netinst:network-instances/oc-netinst:network-instance/oc-netinst:protocols/oc-netinst:protocol/oc-netinst:pim/oc-netinst:interfaces/oc-netinst:interface/oc-netinst:config/oc-netinst:dr-priority {
      deviate add {
          sonic-ext:field-name "dr-priority";
      }
  }

  deviation /oc-netinst:network-instances/oc-netinst:network-instance/oc-netinst:protocols/oc-netinst:protocol/oc-netinst:pim/oc-netinst:interfaces/oc-netinst:interface/oc-netinst:config/oc-netinst:hello-interval {
      deviate add {
          sonic-ext:field-name "hello-interval";
      }
  }

  deviation /oc-netinst:network-instances/oc-netinst:network-instance/oc-netinst:protocols/oc-netinst:protocol/oc-netinst:pim/oc-netinst:interfaces/oc-netinst:interface/oc-netinst:enable-bfd/oc-netinst:config/oc-netinst:enabled {
      deviate add {
          sonic-ext:field-name "bfd-enabled";
      }
  }

  deviation /oc-netinst:network-instances/oc-netinst:network-instance/oc-netinst:protocols/oc-netinst:protocol/oc-netinst:pim/oc-netinst:interfaces/oc-netinst:interface/oc-netinst:enable-bfd/oc-netinst:state {
      deviate add {
          sonic-ext:subscribe-on-change "disable";
      }
  }

  deviation /oc-netinst:network-instances/oc-netinst:network-instance/oc-netinst:protocols/oc-netinst:protocol/oc-netinst:pim/oc-netinst:interfaces/oc-netinst:interface/oc-netinst:enable-bfd/oc-netinst:state/oc-netinst:enabled {
      deviate add {
          sonic-ext:field-name "bfd-enabled";
      }
  }

  deviation /oc-netinst:network-instances/oc-netinst:network-instance/oc-netinst:protocols/oc-netinst:protocol/oc-netinst:pim/oc-netinst:interfaces/oc-netinst:interface/oc-netinst:enable-bfd/oc-netinst:config/oc-netinst:bfd-profile {
      deviate add {
          sonic-ext:field-name "bfd-profile";
      }
  }

  deviation /oc-netinst:network-instances/oc-netinst:network-instance/oc-netinst:protocols/oc-netinst:protocol/oc-netinst:pim/oc-netinst:interfaces/oc-netinst:interface/oc-netinst:enable-bfd/oc-netinst:state/oc-netinst:bfd-profile {
      deviate add {
          sonic-ext:field-name "bfd-profile";
      }
  }

  deviation /oc-netinst:network-instances/oc-netinst:network-instance/oc-netinst:protocols/oc-netinst:protocol/oc-netinst:pim/oc-netinst:interfaces/oc-netinst:interface/oc-netinst:state {
      deviate add {
          sonic-ext:subtree-transformer "pim_intf_state_xfmr";
          sonic-ext:subscribe-on-change "disable";
      }
  }

  deviation /oc-netinst:network-instances/oc-netinst:network-instance/oc-netinst:protocols/oc-netinst:protocol/oc-netinst:pim/oc-netinst:interfaces/oc-netinst:interface/oc-netinst:neighbors {
      deviate add {
          sonic-ext:subtree-transformer "pim_nbrs_state_xfmr";
          sonic-ext:subscribe-on-change "disable";
      }
  }

  deviation /oc-netinst:network-instances/oc-netinst:network-instance/oc-netinst:protocols/oc-netinst:protocol/oc-netinst:pim/oc-netinst:interfaces/oc-netinst:interface/oc-netinst:state/oc-netinst:counters {
      deviate add {
          sonic-ext:subtree-transformer "pim_intf_traffic_xfmr";
          sonic-ext:subscribe-on-change "disable";
      }
   }

    deviation /oc-netinst:network-instances/oc-netinst:network-instance/oc-netinst:evpn/oc-netinst:ethernet-segments/oc-netinst:ethernet-segment/oc-netinst:config/oc-netinst:esi {
      deviate add {
        sonic-ext:field-transformer "evpn_eth_seg_esi_field_xfmr";
      }
    }

    deviation /oc-netinst:network-instances/oc-netinst:network-instance/oc-netinst:evpn/oc-netinst:ethernet-segments/oc-netinst:ethernet-segment/oc-netinst:config/oc-netinst:esi-type {
      deviate add {
        sonic-ext:field-name "esi_type";
      }
    }

    deviation /oc-netinst:network-instances/oc-netinst:network-instance/oc-netinst:evpn/oc-netinst:ethernet-segments/oc-netinst:ethernet-segment/oc-netinst:config/oc-netinst:interface{
      deviate add {
        sonic-ext:field-name "ifname";
      }
    }

    deviation /oc-netinst:network-instances/oc-netinst:network-instance/oc-netinst:evpn/oc-netinst:ethernet-segments/oc-netinst:ethernet-segment/oc-netinst:df-election/oc-netinst:config/oc-netinst:preference{
      deviate add {
        sonic-ext:field-name "df_pref";
      }
    }

    deviation /oc-netinst:network-instances/oc-netinst:network-instance/oc-netinst:evpn/oc-netinst:ethernet-segments/oc-netinst:ethernet-segment{
      deviate add {
        sonic-ext:table-name "EVPN_ETHERNET_SEGMENT";
        sonic-ext:key-transformer "evpn_eth_seq_tbl_xfmr";
      }
    }

    deviation /oc-netinst:network-instances/oc-netinst:network-instance/oc-netinst:evpn/oc-netinst:evpn-mh/oc-netinst:config/oc-netinst:startup-delay{
      deviate add {
        sonic-ext:field-name "startup_delay";
      }
    }

    deviation /oc-netinst:network-instances/oc-netinst:network-instance/oc-netinst:evpn/oc-netinst:evpn-mh/oc-netinst:config/oc-netinst:mac-holdtime{
      deviate add {
        sonic-ext:field-name "mac_holdtime";
      }
    }

    deviation /oc-netinst:network-instances/oc-netinst:network-instance/oc-netinst:evpn/oc-netinst:evpn-mh/oc-netinst:config/oc-netinst:neigh-holdtime{
      deviate add {
        sonic-ext:field-name "neigh_holdtime";
      }
    }

    deviation /oc-netinst:network-instances/oc-netinst:network-instance/oc-netinst:evpn/oc-netinst:evpn-mh/oc-netinst:config/oc-netinst:df-election-time{
      deviate add {
        sonic-ext:field-name "df_election_time";
      }
    }

    deviation /oc-netinst:network-instances/oc-netinst:network-instance/oc-netinst:evpn/oc-netinst:evpn-mh/oc-netinst:config/oc-netinst:es-activation-delay{
      deviate add {
        sonic-ext:field-name "es_activation_delay";
      }
    }

    deviation /oc-netinst:network-instances/oc-netinst:network-instance/oc-netinst:evpn/oc-netinst:evpn-mh{
      deviate add {
        sonic-ext:table-name "EVPN_MH_GLOBAL";
      }
    }
}
