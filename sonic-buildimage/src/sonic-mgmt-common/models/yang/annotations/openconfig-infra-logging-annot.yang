module openconfig-infra-logging-annot {

    yang-version "1";

    namespace "http://openconfig.net/yang/infra-logging-annot";
    prefix "oc-infra-logging-annot";

    import sonic-extensions { prefix sonic-ext; }
    import openconfig-infra-logging { prefix oc-infra-logging; }

    deviation /oc-infra-logging:show-sys-log{
        deviate add {
            sonic-ext:rpc-callback "rpc_infra_show_sys_log_cb";
            sonic-ext:user-role-priv "rpc:secadmin";
        }
    }

    deviation /oc-infra-logging:clear-sys-log{
        deviate add {
            sonic-ext:rpc-callback "rpc_infra_clear_sys_log_cb";
            sonic-ext:user-role-priv "rpc:secadmin";
        }
    }

    deviation /oc-infra-logging:sys-log-count{
        deviate add {
            sonic-ext:rpc-callback "rpc_infra_sys_log_count_cb";
            sonic-ext:user-role-priv "rpc:secadmin";
        }
    }


    deviation /oc-infra-logging:set-loglevel-severity{
        deviate add {
            sonic-ext:rpc-callback "rpc_infra_set_loglevel_severity_cb";
            sonic-ext:user-role-priv "rpc:secadmin";
        }
    }
    deviation /oc-infra-logging:get-loglevel-severity{
        deviate add {
            sonic-ext:rpc-callback "rpc_infra_get_loglevel_severity_cb";
            sonic-ext:user-role-priv "rpc:operator";
        }
    }
    deviation /oc-infra-logging:show-sys-in-memory-log{
        deviate add {
            sonic-ext:rpc-callback "rpc_infra_show_sys_in_memory_log_cb";
            sonic-ext:user-role-priv "rpc:secadmin";
        }
    }
    deviation /oc-infra-logging:sys-in-memory-log-count{
        deviate add {
            sonic-ext:rpc-callback "rpc_infra_sys_in_memory_log_count_cb";
            sonic-ext:user-role-priv "rpc:secadmin";
        }
    }
    deviation /oc-infra-logging:show-memory-hist{
        deviate add {
            sonic-ext:rpc-callback "rpc_infra_show_memory_hist_cb";
            sonic-ext:user-role-priv "rpc:secadmin";
        }
    }

    deviation /oc-infra-logging:logger{
        deviate add {
            sonic-ext:rpc-callback "rpc_infra_logger_cb";
            sonic-ext:user-role-priv "rpc:secadmin";
        }
    }

    deviation /oc-infra-logging:reboot-ops{
        deviate add {
            sonic-ext:rpc-callback "rpc_infra_reboot_cb";
            sonic-ext:user-role-priv "rpc:secadmin";
        }
    }
}
