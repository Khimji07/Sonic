module openconfig-image-management-annot {

    yang-version "1";

    namespace "http://openconfig.net/yang/image-management-annot";
    prefix "oc-img-mgmt-annot";

    import sonic-extensions { prefix sonic-ext; }
    import openconfig-image-management { prefix oc-img-mgmt; }

    // meta
    organization
       "SONiC";

    contact
       "SONiC";

    description
       "SONIC Image Management";

    revision 2020-07-20 {
       description
          "Initial revision.";
    }

    deviation /oc-img-mgmt:image-install {
        deviate add {
            sonic-ext:rpc-callback "rpc_oc_image_install";
        }
    }
    deviation /oc-img-mgmt:image-install-cancel {
        deviate add {
            sonic-ext:rpc-callback "rpc_oc_image_cancel";
        }
    }
    deviation /oc-img-mgmt:image-remove {
        deviate add {
            sonic-ext:rpc-callback "rpc_oc_image_remove";
        }
    }
    deviation /oc-img-mgmt:image-default {
        deviate add {
            sonic-ext:rpc-callback "rpc_oc_image_default";
        }
    }
    deviation /oc-img-mgmt:do-patch-install {
        deviate add {
            sonic-ext:rpc-callback "rpc_oc_patch_install";
        }
    }
    deviation /oc-img-mgmt:do-patch-rollback {
        deviate add {
            sonic-ext:rpc-callback "rpc_oc_patch_rollback";
        }
    }
    deviation /oc-img-mgmt:do-fwpkg-install {
        deviate add {
            sonic-ext:rpc-callback "rpc_oc_fwpkg_install";
        }
    }
    deviation /oc-img-mgmt:do-fwpkg-install-cancel {
        deviate add {
            sonic-ext:rpc-callback "rpc_oc_fwpkg_cancel";
        }
    }

    deviation /oc-img-mgmt:image-management/oc-img-mgmt:global {
      deviate add {
      sonic-ext:table-name "IMAGE_GLOBAL";
      sonic-ext:key-transformer "image_global_key_xfmr";
      sonic-ext:db-name "STATE_DB";      
      }
    }

    deviation /oc-img-mgmt:image-management/oc-img-mgmt:images/oc-img-mgmt:image {
      deviate add {
      sonic-ext:table-name "IMAGE_TABLE";
      sonic-ext:key-transformer "image_table_key_xfmr";
      sonic-ext:db-name "STATE_DB";
      }
    }


    deviation /oc-img-mgmt:image-management/oc-img-mgmt:images/oc-img-mgmt:image/oc-img-mgmt:state/oc-img-mgmt:image-name {
      deviate add {
        sonic-ext:field-transformer "image_name_xfmr";
      }
    }

    deviation /oc-img-mgmt:patch-management/oc-img-mgmt:patch-list/oc-img-mgmt:patch {
      deviate add {
      sonic-ext:table-name "PATCH_LIST";
      sonic-ext:key-transformer "patch_list_key_xfmr";
      sonic-ext:db-name "STATE_DB";
      }
    }
    deviation /oc-img-mgmt:patch-management/oc-img-mgmt:patch-history/oc-img-mgmt:patch {
      deviate add {
      sonic-ext:table-name "PATCH_HISTORY";
      sonic-ext:key-transformer "patch_history_key_xfmr";
      sonic-ext:db-name "STATE_DB";
      }
    }

    deviation /oc-img-mgmt:patch-management/oc-img-mgmt:patch-list/oc-img-mgmt:patch/oc-img-mgmt:state/oc-img-mgmt:id {
      deviate add {
        sonic-ext:field-name "id";
      }
    }
    deviation /oc-img-mgmt:patch-management/oc-img-mgmt:patch-list/oc-img-mgmt:patch/oc-img-mgmt:state/oc-img-mgmt:tag {
      deviate add {
        sonic-ext:field-name "tag";
      }
    }
    deviation /oc-img-mgmt:patch-management/oc-img-mgmt:patch-list/oc-img-mgmt:patch/oc-img-mgmt:state/oc-img-mgmt:date {
      deviate add {
        sonic-ext:field-name "date";
      }
    }
    deviation /oc-img-mgmt:patch-management/oc-img-mgmt:patch-list/oc-img-mgmt:patch/oc-img-mgmt:state/oc-img-mgmt:dependency {
      deviate add {
        sonic-ext:field-name "dependson";
      }
    }
    deviation /oc-img-mgmt:patch-management/oc-img-mgmt:patch-history/oc-img-mgmt:patch/oc-img-mgmt:state/oc-img-mgmt:start {
      deviate add {
        sonic-ext:field-name "start_time";
      }
    }
    deviation /oc-img-mgmt:patch-management/oc-img-mgmt:patch-history/oc-img-mgmt:patch/oc-img-mgmt:state/oc-img-mgmt:end {
      deviate add {
        sonic-ext:field-name "end_time";
      }
    }
    deviation /oc-img-mgmt:patch-management/oc-img-mgmt:patch-history/oc-img-mgmt:patch/oc-img-mgmt:state/oc-img-mgmt:id {
      deviate add {
        sonic-ext:field-name "id";
      }
    }
    deviation /oc-img-mgmt:patch-management/oc-img-mgmt:patch-history/oc-img-mgmt:patch/oc-img-mgmt:state/oc-img-mgmt:tag {
      deviate add {
        sonic-ext:field-name "tag";
      }
    }
    deviation /oc-img-mgmt:patch-management/oc-img-mgmt:patch-history/oc-img-mgmt:patch/oc-img-mgmt:state/oc-img-mgmt:state {
      deviate add {
        sonic-ext:field-name "state";
      }
    }
    deviation /oc-img-mgmt:patch-management/oc-img-mgmt:patch-history/oc-img-mgmt:patch/oc-img-mgmt:state/oc-img-mgmt:status {
      deviate add {
        sonic-ext:field-name "status";
      }
    }

    deviation /oc-img-mgmt:image-management/oc-img-mgmt:install/oc-img-mgmt:state {
      deviate add {
      sonic-ext:table-name "IMAGE_GLOBAL";
      sonic-ext:key-transformer "image_global_key_xfmr";
      sonic-ext:db-name "STATE_DB";
      }
    }
    deviation /oc-img-mgmt:image-management/oc-img-mgmt:install/oc-img-mgmt:state/oc-img-mgmt:operation-status {
      deviate add {
        sonic-ext:field-name "global_state_image";
      }
    }
    deviation /oc-img-mgmt:image-management/oc-img-mgmt:install/oc-img-mgmt:state/oc-img-mgmt:transfer-status {
      deviate add {
        sonic-ext:field-name "transfer_task_state";
      }
    }
    deviation /oc-img-mgmt:image-management/oc-img-mgmt:install/oc-img-mgmt:state/oc-img-mgmt:transfer-status-detail {
      deviate add {
        sonic-ext:field-name "transfer_task_state_detail";
      }
    }
    deviation /oc-img-mgmt:image-management/oc-img-mgmt:install/oc-img-mgmt:state/oc-img-mgmt:install-status {
      deviate add {
        sonic-ext:field-name "install_task_state";
      }
    }
    deviation /oc-img-mgmt:image-management/oc-img-mgmt:install/oc-img-mgmt:state/oc-img-mgmt:install-status-detail {
      deviate add {
        sonic-ext:field-name "install_task_state_detail";
      }
    }

    deviation /oc-img-mgmt:image-management/oc-img-mgmt:install/oc-img-mgmt:state/oc-img-mgmt:transfer-start-time {
      deviate add {
        sonic-ext:field-transformer "transfer_start_time_xfmr";
      }
    }
    deviation /oc-img-mgmt:image-management/oc-img-mgmt:install/oc-img-mgmt:state/oc-img-mgmt:transfer-end-time {
      deviate add {
        sonic-ext:field-transformer "transfer_end_time_xfmr";
      }
    }
    deviation /oc-img-mgmt:image-management/oc-img-mgmt:install/oc-img-mgmt:state/oc-img-mgmt:install-start-time {
      deviate add {
        sonic-ext:field-transformer "install_start_time_xfmr";
      }
    }
    deviation /oc-img-mgmt:image-management/oc-img-mgmt:install/oc-img-mgmt:state/oc-img-mgmt:install-end-time {
      deviate add {
        sonic-ext:field-transformer "install_end_time_xfmr";
      }
    }

    deviation /oc-img-mgmt:image-management/oc-img-mgmt:install/oc-img-mgmt:state/oc-img-mgmt:file-progress {
      deviate add {
        sonic-ext:field-name "file_progress";
      }
    }
    deviation /oc-img-mgmt:image-management/oc-img-mgmt:install/oc-img-mgmt:state/oc-img-mgmt:file-size {
      deviate add {
        sonic-ext:field-name "file_size";
      }
    }
    deviation /oc-img-mgmt:image-management/oc-img-mgmt:install/oc-img-mgmt:state/oc-img-mgmt:file-transfer-bytes {
      deviate add {
        sonic-ext:field-name "file_transfer_bytes";
      }
    }
    deviation /oc-img-mgmt:image-management/oc-img-mgmt:install/oc-img-mgmt:state/oc-img-mgmt:file-download-speed {
      deviate add {
        sonic-ext:field-name "file_download_speed";
      }
    }

    deviation /oc-img-mgmt:patch-management/oc-img-mgmt:patch-install/oc-img-mgmt:download-state {
      deviate add {
      sonic-ext:table-name "IMAGE_PATCH_GLOBAL";
      sonic-ext:key-transformer "image_patch_global_key_xfmr";
      sonic-ext:db-name "STATE_DB";
      }
    }
    deviation /oc-img-mgmt:patch-management/oc-img-mgmt:patch-install/oc-img-mgmt:download-state/oc-img-mgmt:transfer-status {
      deviate add {
        sonic-ext:field-name "transfer_task_state";
      }
    }
    deviation /oc-img-mgmt:patch-management/oc-img-mgmt:patch-install/oc-img-mgmt:download-state/oc-img-mgmt:transfer-status-detail {
      deviate add {
        sonic-ext:field-name "transfer_task_state_detail";
      }
    }
    deviation /oc-img-mgmt:patch-management/oc-img-mgmt:patch-install/oc-img-mgmt:download-state/oc-img-mgmt:transfer-start-time {
      deviate add {
        sonic-ext:field-name "transfer_task_start_time";
      }
    }
    deviation /oc-img-mgmt:patch-management/oc-img-mgmt:patch-install/oc-img-mgmt:download-state/oc-img-mgmt:transfer-end-time {
      deviate add {
        sonic-ext:field-name "transfer_task_end_time";
      }
    }
    deviation /oc-img-mgmt:patch-management/oc-img-mgmt:patch-install/oc-img-mgmt:download-state/oc-img-mgmt:file-progress {
      deviate add {
        sonic-ext:field-name "file_progress";
      }
    }
    deviation /oc-img-mgmt:patch-management/oc-img-mgmt:patch-install/oc-img-mgmt:download-state/oc-img-mgmt:file-size {
      deviate add {
        sonic-ext:field-name "file_size";
      }
    }
    deviation /oc-img-mgmt:patch-management/oc-img-mgmt:patch-install/oc-img-mgmt:download-state/oc-img-mgmt:file-transfer-bytes {
      deviate add {
        sonic-ext:field-name "file_transfer_bytes";
      }
    }

    deviation /oc-img-mgmt:patch-management/oc-img-mgmt:patch-install/oc-img-mgmt:install-state {
      deviate add {
      sonic-ext:table-name "PATCH_CURRENT";
      sonic-ext:key-transformer "patch_current_key_xfmr";
      sonic-ext:db-name "STATE_DB";
      }
    }
    deviation /oc-img-mgmt:patch-management/oc-img-mgmt:patch-install/oc-img-mgmt:install-state/oc-img-mgmt:trigger {
      deviate add {
        sonic-ext:field-name "trigger";
      }
    }
    deviation /oc-img-mgmt:patch-management/oc-img-mgmt:patch-install/oc-img-mgmt:install-state/oc-img-mgmt:install-status {
      deviate add {
        sonic-ext:field-name "install_status";
      }
    }
    deviation /oc-img-mgmt:patch-management/oc-img-mgmt:patch-install/oc-img-mgmt:install-state/oc-img-mgmt:install-start-time {
      deviate add {
        sonic-ext:field-name "install_start";
      }
    }
    deviation /oc-img-mgmt:patch-management/oc-img-mgmt:patch-install/oc-img-mgmt:install-state/oc-img-mgmt:install-end-time {
      deviate add {
        sonic-ext:field-name "install_end";
      }
    }
    deviation /oc-img-mgmt:patch-management/oc-img-mgmt:patch-install/oc-img-mgmt:install-state/oc-img-mgmt:rollback-status {
      deviate add {
        sonic-ext:field-name "rollback_status";
      }
    }
    deviation /oc-img-mgmt:patch-management/oc-img-mgmt:patch-install/oc-img-mgmt:install-state/oc-img-mgmt:rollback-start-time {
      deviate add {
        sonic-ext:field-name "rollback_start";
      }
    }
    deviation /oc-img-mgmt:patch-management/oc-img-mgmt:patch-install/oc-img-mgmt:install-state/oc-img-mgmt:rollback-end-time {
      deviate add {
        sonic-ext:field-name "rollback_end";
      }
    }
    deviation /oc-img-mgmt:patch-management/oc-img-mgmt:patch-install/oc-img-mgmt:install-state/oc-img-mgmt:recovery-status {
      deviate add {
        sonic-ext:field-name "recover_status";
      }
    }
    deviation /oc-img-mgmt:patch-management/oc-img-mgmt:patch-install/oc-img-mgmt:install-state/oc-img-mgmt:recovery-start-time {
      deviate add {
        sonic-ext:field-name "recover_start";
      }
    }
    deviation /oc-img-mgmt:patch-management/oc-img-mgmt:patch-install/oc-img-mgmt:install-state/oc-img-mgmt:recovery-end-time {
      deviate add {
        sonic-ext:field-name "recover_end";
      }
    }

    deviation /oc-img-mgmt:fwpkg-management/oc-img-mgmt:fwpkg-install {
      deviate add {
      sonic-ext:table-name "FWPKG_CURRENT";
      sonic-ext:key-transformer "fwpkg_current_key_xfmr";
      sonic-ext:db-name "STATE_DB";
      }
    }
    deviation /oc-img-mgmt:fwpkg-management/oc-img-mgmt:fwpkg-pending/oc-img-mgmt:fwpkg {
      deviate add {
        sonic-ext:table-name "FWPKG_PENDING";
        sonic-ext:db-name "STATE_DB";
      }
    }
    deviation /oc-img-mgmt:fwpkg-management/oc-img-mgmt:fwpkg-result/oc-img-mgmt:fwpkg {
      deviate add {
        sonic-ext:table-name "FWPKG_RESULT";
        sonic-ext:db-name "STATE_DB";
      }
    }

    deviation /oc-img-mgmt:fwpkg-management/oc-img-mgmt:fwpkg-install/oc-img-mgmt:download-state/oc-img-mgmt:file-download-speed {
      deviate add {
        sonic-ext:field-name "file_download_speed";
      }
    }
    deviation /oc-img-mgmt:fwpkg-management/oc-img-mgmt:fwpkg-install/oc-img-mgmt:download-state/oc-img-mgmt:file-progress {
      deviate add {
        sonic-ext:field-name "file_progress";
      }
    }
    deviation /oc-img-mgmt:fwpkg-management/oc-img-mgmt:fwpkg-install/oc-img-mgmt:download-state/oc-img-mgmt:file-size {
      deviate add {
        sonic-ext:field-name "file_size";
      }
    }
    deviation /oc-img-mgmt:fwpkg-management/oc-img-mgmt:fwpkg-install/oc-img-mgmt:download-state/oc-img-mgmt:file-transfer-bytes {
      deviate add {
        sonic-ext:field-name "file_transfer_bytes";
      }
    }
    deviation /oc-img-mgmt:fwpkg-management/oc-img-mgmt:fwpkg-install/oc-img-mgmt:download-state/oc-img-mgmt:transfer-status {
      deviate add {
        sonic-ext:field-name "transfer_task_state";
      }
    }
    deviation /oc-img-mgmt:fwpkg-management/oc-img-mgmt:fwpkg-install/oc-img-mgmt:download-state/oc-img-mgmt:transfer-status-detail {
      deviate add {
        sonic-ext:field-name "transfer_task_state_detail";
      }
    }
    deviation /oc-img-mgmt:fwpkg-management/oc-img-mgmt:fwpkg-install/oc-img-mgmt:download-state/oc-img-mgmt:transfer-start-time {
      deviate add {
        sonic-ext:field-transformer "fwpkg_transfer_start_time_xfmr";
      }
    }
    deviation /oc-img-mgmt:fwpkg-management/oc-img-mgmt:fwpkg-install/oc-img-mgmt:download-state/oc-img-mgmt:transfer-end-time {
      deviate add {
        sonic-ext:field-transformer "fwpkg_transfer_end_time_xfmr";
      }
    }

    deviation /oc-img-mgmt:fwpkg-management/oc-img-mgmt:fwpkg-install/oc-img-mgmt:stage-state/oc-img-mgmt:stage-status {
      deviate add {
        sonic-ext:field-name "stage_task_state";
      }
    }
    deviation /oc-img-mgmt:fwpkg-management/oc-img-mgmt:fwpkg-install/oc-img-mgmt:stage-state/oc-img-mgmt:stage-status-detail {
      deviate add {
        sonic-ext:field-name "stage_task_state_detail";
      }
    }
    deviation /oc-img-mgmt:fwpkg-management/oc-img-mgmt:fwpkg-install/oc-img-mgmt:stage-state/oc-img-mgmt:stage-start-time {
      deviate add {
        sonic-ext:field-transformer "fwpkg_stage_start_time_xfmr";
      }
    }
    deviation /oc-img-mgmt:fwpkg-management/oc-img-mgmt:fwpkg-install/oc-img-mgmt:stage-state/oc-img-mgmt:stage-end-time {
      deviate add {
        sonic-ext:field-transformer "fwpkg_stage_end_time_xfmr";
      }
    }

    deviation /oc-img-mgmt:fwpkg-management/oc-img-mgmt:fwpkg-pending/oc-img-mgmt:fwpkg/oc-img-mgmt:state/oc-img-mgmt:date {
      deviate add {
        sonic-ext:field-name "date";
      }
    }
    deviation /oc-img-mgmt:fwpkg-management/oc-img-mgmt:fwpkg-pending/oc-img-mgmt:fwpkg/oc-img-mgmt:state/oc-img-mgmt:version {
      deviate add {
        sonic-ext:field-name "version";
      }
    }

    deviation /oc-img-mgmt:fwpkg-management/oc-img-mgmt:fwpkg-result/oc-img-mgmt:fwpkg/oc-img-mgmt:state/oc-img-mgmt:date {
      deviate add {
        sonic-ext:field-name "date";
      }
    }
    deviation /oc-img-mgmt:fwpkg-management/oc-img-mgmt:fwpkg-result/oc-img-mgmt:fwpkg/oc-img-mgmt:state/oc-img-mgmt:result {
      deviate add {
        sonic-ext:field-name "result";
      }
    }
    deviation /oc-img-mgmt:fwpkg-management/oc-img-mgmt:fwpkg-result/oc-img-mgmt:fwpkg/oc-img-mgmt:state/oc-img-mgmt:version {
      deviate add {
        sonic-ext:field-name "version";
      }
    }
}
