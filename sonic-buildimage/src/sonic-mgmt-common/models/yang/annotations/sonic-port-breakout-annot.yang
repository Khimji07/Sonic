module sonic-port-breakout-annot {

    yang-version "1";

    namespace "http://openconfig.net/yang/annotation/sbrkprt-annot";
    prefix "sbrkprt-annot";

    import sonic-extensions { prefix sonic-ext; }
    import sonic-port-breakout { prefix sbrkprt; }

    deviation /sbrkprt:breakout_dependencies {
      deviate add {
        sonic-ext:rpc-callback "rpc_breakout_dependencies";
	sonic-ext:user-role-priv "rpc:operator";
      }
    }

    deviation /sbrkprt:breakout_capabilities {
      deviate add {
        sonic-ext:rpc-callback "rpc_breakout_capabilities";
	sonic-ext:user-role-priv "rpc:operator";
      }
    }

    deviation /sbrkprt:breakout_resources {
      deviate add {
        sonic-ext:rpc-callback "rpc_breakout_resources";
      }
    }

    deviation /sbrkprt:sonic-port-breakout {
        deviate add {
            sonic-ext:user-role-priv "write:netadmin";
        }
    }

    deviation /sbrkprt:sonic-port-breakout/sbrkprt:BREAKOUT_CFG/sbrkprt:BREAKOUT_CFG_LIST/sbrkprt:ifname {
        deviate add {
            sonic-ext:value-transformer "alias_value_xfmr";
        }
    }

    deviation /sbrkprt:sonic-port-breakout/sbrkprt:PORT_BREAKOUT/sbrkprt:PORT_BREAKOUT_LIST/sbrkprt:ifname {
        deviate add {
            sonic-ext:value-transformer "alias_value_xfmr";
        }
    }

    deviation /sbrkprt:sonic-port-breakout/sbrkprt:BREAKOUT_PORTS/sbrkprt:BREAKOUT_PORTS_LIST/sbrkprt:ifname {
        deviate add {
            sonic-ext:value-transformer "alias_value_xfmr";
        }
    }

    deviation /sbrkprt:sonic-port-breakout/sbrkprt:BREAKOUT_PORTS/sbrkprt:BREAKOUT_PORTS_LIST/sbrkprt:master {
        deviate add {
            sonic-ext:value-transformer "alias_value_xfmr";
        }
    }

}
