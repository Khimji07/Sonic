module sonic-qos-pfc-annot {

    yang-version "1.1";

    namespace "http://openconfig.net/yang/sqpw-annot";
    prefix "sqpw-annot";

    import sonic-qos-pfc { prefix sqpw; }
    import sonic-extensions { prefix sonic-ext; }

    deviation /sqpw:sonic-qos-pfc/sqpw:PFC_WD/sqpw:PFC_WD_LIST/sqpw:ifname {
      deviate add {
            sonic-ext:value-transformer "alias_value_xfmr";
      }
    }
}
