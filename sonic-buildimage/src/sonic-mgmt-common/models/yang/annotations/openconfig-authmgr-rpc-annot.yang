module openconfig-authmgr-rpc-annot {

    yang-version "1.1";

    namespace "http://openconfig.net/yang/annotation/oc-authmgr-rpc-annot";
    prefix "oc-authmgr-rpc-annot";

    import sonic-extensions { prefix sonic-ext; }
    import openconfig-authmgr-rpc { prefix oc-authmgr-rpc; }

    deviation /oc-authmgr-rpc:clear-authmgr-sessions {
             deviate add {
                    sonic-ext:rpc-callback "rpc_clear_authmgr_sessions";
                    sonic-ext:user-role-priv "rpc:netadmin"; 
             }
    }

    deviation /oc-authmgr-rpc:clear-authmgr-history {
             deviate add {
                    sonic-ext:rpc-callback "rpc_clear_authmgr_history";
                    sonic-ext:user-role-priv "rpc:netadmin"; 
             }
    }
}
