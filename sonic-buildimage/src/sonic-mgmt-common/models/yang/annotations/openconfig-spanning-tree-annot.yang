module openconfig-spanning-tree-annot {

    yang-version "1.1";

    namespace "http://openconfig.net/yang/spanning-tree-annot";
    prefix "oc-stp-annot";

    import sonic-extensions { prefix sonic-ext; }
    import openconfig-spanning-tree { prefix oc-stp; }
    import openconfig-spanning-tree-ext { prefix oc-stp-ext; }

    // meta
    organization
       "SONiC";

    contact
       "SONiC";

    description
       "SONIC STP";

    revision 2020-04-16 {
       description
          "Initial revision.";
    }

    deviation /oc-stp:stp {
        deviate add {
            sonic-ext:user-role-priv "write:netadmin";
        }
    }

    deviation /oc-stp:stp {
        deviate add {
            sonic-ext:pre-transformer "stp_pre_xfmr";
            sonic-ext:post-transformer "stp_post_xfmr";
        }
    }

    deviation /oc-stp:stp/oc-stp:global {
        deviate add {
            sonic-ext:subtree-transformer "stp_global_xfmr";
        }
    }

    deviation /oc-stp:stp/oc-stp:rapid-pvst/oc-stp:vlan {
        deviate add {
            sonic-ext:subtree-transformer "stp_vlan_xfmr";
        }
    }

    deviation /oc-stp:stp/oc-stp:rapid-pvst/oc-stp:vlan/oc-stp:interfaces/oc-stp:interface {
        deviate add {
            sonic-ext:subtree-transformer "stp_vlan_port_xfmr";
        }
    }

    deviation /oc-stp:stp/oc-stp:interfaces/oc-stp:interface { 
        deviate add {
            sonic-ext:table-name "STP_PORT";
        }
    }

    deviation /oc-stp:stp/oc-stp:interfaces/oc-stp:interface/oc-stp:config { 
        deviate add {
            sonic-ext:subtree-transformer "stp_port_xfmr";
        }
    }

    deviation /oc-stp:stp/oc-stp:interfaces/oc-stp:interface/oc-stp:state { 
        deviate add {
            sonic-ext:subtree-transformer "stp_port_xfmr";
        }
    }

    deviation /oc-stp:stp/oc-stp-ext:pvst/oc-stp-ext:vlans {
        deviate add {
            sonic-ext:subtree-transformer "stp_vlan_xfmr";
        }
    }

    deviation /oc-stp:stp/oc-stp-ext:pvst/oc-stp-ext:vlans/oc-stp-ext:interfaces/oc-stp-ext:interface {
        deviate add {
            sonic-ext:subtree-transformer "stp_vlan_port_xfmr";
        }
    }

    deviation /oc-stp:stp/oc-stp:mstp/oc-stp:config {
        deviate add {
            sonic-ext:table-name "STP_MST";
            sonic-ext:key-transformer "stp_mst_key_xfmr";
        }
    }

    deviation /oc-stp:stp/oc-stp:mstp/oc-stp:config/oc-stp:max-hop {
        deviate add {
            sonic-ext:field-name "max_hops";
        }
    }

    deviation /oc-stp:stp/oc-stp:mstp/oc-stp:config/oc-stp:hello-time {
        deviate add {
            sonic-ext:field-name "hello_time";
        }
    }

    deviation /oc-stp:stp/oc-stp:mstp/oc-stp:config/oc-stp:forwarding-delay {
        deviate add {
            sonic-ext:field-name "forward_delay";
        }
    }

    deviation /oc-stp:stp/oc-stp:mstp/oc-stp:config/oc-stp:max-age {
        deviate add {
            sonic-ext:field-name "max_age";
        }
    }

    deviation /oc-stp:stp/oc-stp:mstp/oc-stp:state {
        deviate add {
            sonic-ext:table-name "STP_MST";
            sonic-ext:key-transformer "stp_mst_key_xfmr";
        }
    }

    deviation /oc-stp:stp/oc-stp:mstp/oc-stp:state/oc-stp:max-hop {
        deviate add {
            sonic-ext:field-name "max_hops";
        }
    }

    deviation /oc-stp:stp/oc-stp:mstp/oc-stp:state/oc-stp-ext:digest {
        deviate add {
            sonic-ext:db-name "APPL_DB";
            sonic-ext:table-name "_STP_MST_DIGEST_TABLE";
            sonic-ext:field-transformer "stp_mst_digest_xfmr";
        }
    }

    deviation /oc-stp:stp/oc-stp:mstp/oc-stp:state/oc-stp-ext:name {
        deviate add {
            sonic-ext:db-name "APPL_DB";
            sonic-ext:table-name "_STP_MST_NAME_TABLE";
            sonic-ext:field-transformer "stp_mst_name_xfmr";
        }
    }


    deviation /oc-stp:stp/oc-stp:mstp/oc-stp:state/oc-stp:hello-time {
        deviate add {
            sonic-ext:field-name "hello_time";
        }
    }

    deviation /oc-stp:stp/oc-stp:mstp/oc-stp:state/oc-stp:forwarding-delay {
        deviate add {
            sonic-ext:field-name "forward_delay";
        }
    }

    deviation /oc-stp:stp/oc-stp:mstp/oc-stp:state/oc-stp:max-age {
        deviate add {
            sonic-ext:field-name "max_age";
        }
    }

    deviation /oc-stp:stp/oc-stp:mstp/oc-stp:mst-instances/oc-stp:mst-instance {
        deviate add {
            sonic-ext:table-name "STP_MST_INST";
            sonic-ext:key-transformer "stp_mst_inst_key_xfmr";
        }
    }

    deviation /oc-stp:stp/oc-stp:mstp/oc-stp:mst-instances/oc-stp:mst-instance/oc-stp:config/oc-stp:bridge-priority {
        deviate add {
            sonic-ext:field-name "bridge_priority";
        }
    }

    deviation /oc-stp:stp/oc-stp:mstp/oc-stp:mst-instances/oc-stp:mst-instance/oc-stp:config/oc-stp:vlan {
        deviate add {
            sonic-ext:field-transformer "stp_mst_inst_vlan_xfmr";
        }
    }

    deviation /oc-stp:stp/oc-stp:mstp/oc-stp:mst-instances/oc-stp:mst-instance/oc-stp:state {
        deviate add {
            sonic-ext:db-name "APPL_DB";
            sonic-ext:table-name "_STP_MST_INST_TABLE";
            sonic-ext:key-transformer "stp_mst_inst_key_xfmr";
        }
    }

    deviation /oc-stp:stp/oc-stp:mstp/oc-stp:mst-instances/oc-stp:mst-instance/oc-stp:state/oc-stp:vlan {
        deviate add {
            sonic-ext:field-transformer "stp_mst_inst_vlan_xfmr";
        }
    }

    deviation /oc-stp:stp/oc-stp:mstp/oc-stp:mst-instances/oc-stp:mst-instance/oc-stp:state/oc-stp:bridge-address {
        deviate add {
            sonic-ext:field-name "bridge_address";
        }
    }

    deviation /oc-stp:stp/oc-stp:mstp/oc-stp:mst-instances/oc-stp:mst-instance/oc-stp:state/oc-stp:designated-root-priority {
        deviate add {
            sonic-ext:field-name "root_priority";
        }
    }

    deviation /oc-stp:stp/oc-stp:mstp/oc-stp:mst-instances/oc-stp:mst-instance/oc-stp:state/oc-stp:designated-root-address {
        deviate add {
            sonic-ext:field-name "root_address";
        }
    }

    deviation /oc-stp:stp/oc-stp:mstp/oc-stp:mst-instances/oc-stp:mst-instance/oc-stp:state/oc-stp:root-cost {
        deviate add {
            sonic-ext:field-name "root_cost";
        }
    }

    deviation /oc-stp:stp/oc-stp:mstp/oc-stp:mst-instances/oc-stp:mst-instance/oc-stp:state/oc-stp:root-port {
        deviate add {
            sonic-ext:field-name "root_port";
        }
    }

    deviation /oc-stp:stp/oc-stp:mstp/oc-stp:mst-instances/oc-stp:mst-instance/oc-stp:state/oc-stp:bridge-priority {
        deviate add {
            sonic-ext:field-name "bridge_priority";
        }
    }

    deviation /oc-stp:stp/oc-stp:mstp/oc-stp:mst-instances/oc-stp:mst-instance/oc-stp:state/oc-stp-ext:root-hello-time {
        deviate add {
            sonic-ext:field-name "root_hello_time";
        }
    }

    deviation /oc-stp:stp/oc-stp:mstp/oc-stp:mst-instances/oc-stp:mst-instance/oc-stp:state/oc-stp-ext:root-max-age {
        deviate add {
            sonic-ext:field-name "root_max_age";
        }
    }

    deviation /oc-stp:stp/oc-stp:mstp/oc-stp:mst-instances/oc-stp:mst-instance/oc-stp:state/oc-stp-ext:root-forward-delay {
        deviate add {
            sonic-ext:field-name "root_forward_delay";
        }
    }

    deviation /oc-stp:stp/oc-stp:mstp/oc-stp:mst-instances/oc-stp:mst-instance/oc-stp:state/oc-stp-ext:regional-root-address {
        deviate add {
            sonic-ext:field-name "regional_root_address";
        }
    }

    deviation /oc-stp:stp/oc-stp:mstp/oc-stp:mst-instances/oc-stp:mst-instance/oc-stp:state/oc-stp:hold-time {
        deviate add {
            sonic-ext:field-name "hold_time";
        }
    }

    deviation /oc-stp:stp/oc-stp:mstp/oc-stp:mst-instances/oc-stp:mst-instance/oc-stp:state/oc-stp:root-cost {
        deviate add {
            sonic-ext:field-name "root_path_cost";
        }
    }

    deviation /oc-stp:stp/oc-stp:mstp/oc-stp:mst-instances/oc-stp:mst-instance/oc-stp:state/oc-stp-ext:root-port-name {
        deviate add {
            sonic-ext:field-name "root_port";
        }
    }

    deviation /oc-stp:stp/oc-stp:mstp/oc-stp:mst-instances/oc-stp:mst-instance/oc-stp:state/oc-stp-ext:remaining-hops {
        deviate add {
            sonic-ext:field-name "remaining_hops";
        }
    }

    deviation /oc-stp:stp/oc-stp:mstp/oc-stp:mst-instances/oc-stp:mst-instance/oc-stp:state/oc-stp-ext:regional-root-cost {
        deviate add {
            sonic-ext:field-name "regional_root_cost";
        }
    }

    deviation /oc-stp:stp/oc-stp:mstp/oc-stp:mst-instances/oc-stp:mst-instance/oc-stp:interfaces/oc-stp:interface {
        deviate add {
            sonic-ext:subtree-transformer "stp_mst_intf_xfmr";
        }
    }
}
