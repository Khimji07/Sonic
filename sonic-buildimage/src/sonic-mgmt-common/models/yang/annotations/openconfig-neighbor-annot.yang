module openconfig-neighbor-annot {

    yang-version "1";

    namespace "http://openconfig.net/yang/annotation/oc-nbr-annot";
    prefix "oc-nbr-annot";

    import openconfig-neighbor { prefix oc-nbr; }
    import sonic-extensions { prefix sonic-ext; }

    deviation /oc-nbr:neighbor-globals {
        deviate add {
            sonic-ext:user-role-priv "write:netadmin";
        }
    }

    deviation /oc-nbr:neighbor-globals/oc-nbr:neighbor-global {
        deviate add {
            sonic-ext:table-name "NEIGH_GLOBAL";
            sonic-ext:key-transformer "neighbor_global_key_xfmr";
        }
    }

    deviation /oc-nbr:neighbor-globals/oc-nbr:neighbor-global/oc-nbr:config/oc-nbr:name {
        deviate add {
            sonic-ext:field-transformer "name_fld_xfmr";
        }
    }

    deviation /oc-nbr:neighbor-globals/oc-nbr:neighbor-global/oc-nbr:config/oc-nbr:ipv4-arp-timeout {
        deviate add {
            sonic-ext:field-name "ipv4_arp_timeout";
        }
    }

    deviation /oc-nbr:neighbor-globals/oc-nbr:neighbor-global/oc-nbr:config/oc-nbr:ipv6-nd-cache-expiry {
        deviate add {
            sonic-ext:field-name "ipv6_nd_cache_expiry";
        }
    }

    deviation /oc-nbr:neighbor-globals/oc-nbr:neighbor-global/oc-nbr:config/oc-nbr:num-local-neigh {
        deviate add {
            sonic-ext:field-name "num_local_neigh";
        }
    }

    deviation /oc-nbr:neighbor-globals/oc-nbr:neighbor-global/oc-nbr:config/oc-nbr:ipv4-drop-neighbor-aging-time {
        deviate add {
            sonic-ext:field-name "ipv4_drop_neighbor_aging_time";
        }
    }

    deviation /oc-nbr:neighbor-globals/oc-nbr:neighbor-global/oc-nbr:config/oc-nbr:ipv6-drop-neighbor-aging-time {
        deviate add {
            sonic-ext:field-name "ipv6_drop_neighbor_aging_time";
        }
    }

    deviation /oc-nbr:neighbor-globals/oc-nbr:neighbor-global/oc-nbr:state/oc-nbr:name {
        deviate add {
            sonic-ext:field-transformer "name_fld_xfmr";
        }
    }

    deviation /oc-nbr:neighbor-globals/oc-nbr:neighbor-global/oc-nbr:state/oc-nbr:ipv4-arp-timeout {
        deviate add {
            sonic-ext:field-name "ipv4_arp_timeout";
        }
    }

    deviation /oc-nbr:neighbor-globals/oc-nbr:neighbor-global/oc-nbr:state/oc-nbr:ipv6-nd-cache-expiry {
        deviate add {
            sonic-ext:field-name "ipv6_nd_cache_expiry";
        }
    }

    deviation /oc-nbr:neighbor-globals/oc-nbr:neighbor-global/oc-nbr:state/oc-nbr:num-local-neigh {
        deviate add {
            sonic-ext:field-name "num_local_neigh";
        }
    }

    deviation /oc-nbr:neighbor-globals/oc-nbr:neighbor-global/oc-nbr:state/oc-nbr:ipv4-drop-neighbor-aging-time {
        deviate add {
            sonic-ext:field-name "ipv4_drop_neighbor_aging_time";
        }
    }

    deviation /oc-nbr:neighbor-globals/oc-nbr:neighbor-global/oc-nbr:state/oc-nbr:ipv6-drop-neighbor-aging-time {
        deviate add {
            sonic-ext:field-name "ipv6_drop_neighbor_aging_time";
        }
    }
}
