module sonic-das-annot {
    namespace "http://github.com/Azure/sonic-das-annot";
    prefix das-annot;
    yang-version 1.1;

    import sonic-extensions { prefix sonic-ext; }
    import sonic-das { prefix sdas; }

    deviation /sdas:sonic-das {
        deviate add {
            sonic-ext:user-role-priv "write:secadmin";
        }
    }

    deviation /sdas:sonic-das/sdas:DAS_CLIENT_COUNTER_TABLE/sdas:DAS_CLIENT_COUNTER_TABLE_LIST {
        deviate add {
            sonic-ext:db-name "COUNTERS_DB";
            sonic-ext:key-transformer "das_client_counter_stats_table_sonic_key_xfmr";
        }
    }

}
