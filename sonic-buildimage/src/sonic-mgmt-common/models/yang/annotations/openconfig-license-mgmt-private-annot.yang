module openconfig-license-mgmt-private-annot {

    yang-version "1.1";

    namespace "http://openconfig.net/yang/license-mgmt-private-annot";
    prefix "oc-license-annot";

    import sonic-extensions { prefix sonic-ext; }

    import openconfig-license-mgmt-private {prefix oc-license; }

    deviation /oc-license:install {
        deviate add {
            sonic-ext:rpc-callback "rpc_install_cb";
        }
    }

    deviation /oc-license:license-management/oc-license:state {
        deviate add {
            sonic-ext:db-name "STATE_DB";
            sonic-ext:subtree-transformer "license_xfmr";
        }
    }

}
