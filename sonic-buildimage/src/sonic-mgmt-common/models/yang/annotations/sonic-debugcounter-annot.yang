module sonic-debugcounter-annot {

    yang-version "1.1";

    namespace "http://openconfig.net/yang/annotation/debugcounter-annot";
    prefix "sonic-debugcoutner-annot";

    import sonic-extensions { prefix sonic-ext; }
    import sonic-debugcounter { prefix debugcounter; }


    deviation /debugcounter:sonic-debugcounter/debugcounter:DEBUG_COUNTER_CAPABILITIES {
        deviate add {
            sonic-ext:table-name "DEBUG_COUNTER_CAPABILITIES";
            sonic-ext:db-name "STATE_DB";
        }
    }
}
