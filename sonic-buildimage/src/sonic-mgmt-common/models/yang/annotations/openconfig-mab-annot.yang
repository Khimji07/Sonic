module openconfig-mab-annot {

    yang-version "1.1";

    namespace "http://openconfig.net/yang/annotation/oc-mab-annot";
    prefix "oc-mab-annot";

    import sonic-extensions { prefix sonic-ext; }
    import openconfig-mab { prefix oc-mab; }

    // meta
    organization
       "SONiC";

    contact
       "SONiC";

    description
       "SONIC PAC";

    revision "2021-07-12" {
    description
      "Initial public revision";
    reference "0.1.0";
    }

	deviation /oc-mab:mab {
		deviate add {
                        sonic-ext:user-role-priv "write:secadmin";
		}
    	}

	deviation /oc-mab:mab/oc-mab:mab-global-config {
		deviate add {
			sonic-ext:subtree-transformer "mab_global_config_xfmr";
		}
    	}

        deviation /oc-mab:mab/oc-mab:mab-port-config/oc-mab:interface {
                deviate add {
			sonic-ext:table-name "MAB_PORT_CONFIG_TABLE";
                }
        }

	deviation /oc-mab:mab/oc-mab:mab-port-config/oc-mab:interface/oc-mab:config {
		deviate add {
			sonic-ext:subtree-transformer "mab_port_config_xfmr";
		}
	}

	deviation /oc-mab:mab/oc-mab:mab-port-config/oc-mab:interface/oc-mab:state {
		deviate add {
			sonic-ext:subtree-transformer "mab_port_config_xfmr";
		}
	}
}
