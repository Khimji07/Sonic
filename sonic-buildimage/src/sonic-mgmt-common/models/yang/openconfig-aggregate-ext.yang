module openconfig-aggregate-ext {

  yang-version "1";

  // namespace
  namespace "http://openconfig.net/yang/aggregate-ext/extension";

  prefix "oc-aggregate-ext";

  // imports
  import openconfig-extensions { prefix oc-ext; }

  // meta
  organization "SONiC";

  contact
    "SONiC";

  description
    "This module defines the global configuration of LAGs";

  oc-ext:openconfig-version "0.1.0";

  revision "2020-05-28" {
    description
      "Initial version";

    reference "0.1.0";
  }

  // extension statements

  // feature statements

  // identity statements

  // typedef statements

  typedef mode {
      type string;
      description
        "Enable/Disable modes";
  }

  // grouping statements
  grouping aggregate-ext-global-config {
    description
      "LAG global config";

    leaf graceful-shutdown-mode {
      type enumeration{
        enum ENABLE;
        enum DISABLE;
      }  
      description
        "Enable/Disable graceful shutdown mode for LAGs";
    }
  }

  grouping aggregate-ext-top {
    description
      "Top level grouping for global LAG data";

    container aggregate {
      description
        "Top level enclosing container for global LAG
        config and operational state data";

      container config {
        description
          "Global config data for LAGs";

        uses aggregate-ext-global-config;
      }

      container state {

        config false;

        description
          "Global operational state data for LAG";

        uses aggregate-ext-global-config;
      }

    }
  }

  // data definition statements
  uses aggregate-ext-top;

  // augment statements

  // rpc statements

  // notification statements
}
